Attribute VB_Name = "CAltitudeSelection"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CAltitudeSelection - Resultat d'une recherche d'altitude
'
' Memorise la valeur altitude trouvee, son origine dans le repere du modele
' actif, l'element source eventuel, et indique si la source vient d'une
' reference attachee. Compatible VBA 6.x : pas de membre Public de type Point3d.
'==============================================================================
Option Explicit

Public ValeurTexte      As String
Public TagDefName       As String
Public EstReference     As Boolean

Public oTexte           As TextElement
Public oTag             As TagElement
Public oCellule         As CellElement
Public oAttachment      As Object

Private m_dX            As Double
Private m_dY            As Double
Private m_dZ            As Double

'------------------------------------------------------------------------------
Sub Vider()
    ValeurTexte = ""
    TagDefName = ""
    EstReference = False
    Set oTexte = Nothing
    Set oTag = Nothing
    Set oCellule = Nothing
    Set oAttachment = Nothing
    m_dX = 0#: m_dY = 0#: m_dZ = 0#
End Sub

'------------------------------------------------------------------------------
Sub DefinirOrigine(oPt As Point3d)
    m_dX = oPt.X
    m_dY = oPt.Y
    m_dZ = oPt.Z
End Sub

'------------------------------------------------------------------------------
Sub CopierOrigine(oPt As Point3d)
    oPt.X = m_dX
    oPt.Y = m_dY
    oPt.Z = m_dZ
End Sub

'------------------------------------------------------------------------------
Sub CopierDepuis(oSrc As CAltitudeSelection)
    If oSrc Is Nothing Then
        Vider
        Exit Sub
    End If

    ValeurTexte = oSrc.ValeurTexte
    TagDefName = oSrc.TagDefName
    EstReference = oSrc.EstReference
    Set oTexte = oSrc.oTexte
    Set oTag = oSrc.oTag
    Set oCellule = oSrc.oCellule
    Set oAttachment = oSrc.oAttachment

    Dim oPt As Point3d
    oSrc.CopierOrigine oPt
    DefinirOrigine oPt
End Sub

'------------------------------------------------------------------------------
Property Get Trouvee() As Boolean
    Trouvee = (Len(ValeurTexte) > 0)
End Property

Attribute VB_Name = "CCalcul"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CCalcul - Moteur de calcul pur de Trans3D
'
' Issu de CInterpolation (InterpolationTopo), elague de la projection P1-P2
' et enrichi du calcul curviligne pour la conversion 2D -> 3D.
'
' Responsabilites :
'   - parsing d'un texte altitude (numerique, separateur, decimales)
'   - abscisses curvilignes d'une polyligne (2D et 3D)
'   - point / tangente a une abscisse donnee sur une polyligne
'   - projection d'un point sur une polyligne (abscisse de la cote cliquee)
'   - semis d'abscisses : pas fixe ou parts egales
'   - interpolation d'altitude par troncons (refs depart/fin/intermediaires)
'   - pente, formatage
'
' Conventions :
'   - toutes les polylignes sont des tableaux Double ; les tableaux de sortie
'     sont ReDim en 0-based par cette classe
'   - les abscisses de reference (dSRef/dZRef) sont triees par
'     TrierRefsParAbscisse avant toute interpolation
'
' Cette classe ne connait pas : symbologie, niveaux, elements MST, formulaire.
' Seule exception heritee : LireAltitudeTexte lit g_oSelectionCourante
' (resultat de RechercheAltitude) et le type Point3d (UDT simple).
'==============================================================================
Option Explicit

Private Const PI As Double = 3.14159265358979
Private Const EPSILON As Double = 0.0000000001
Private Const DIST_MIN As Double = 0.001    ' points confondus : ~1 mm

'==============================================================================
' Parsing
'==============================================================================

'------------------------------------------------------------------------------
' Vrai si s est un nombre au format normalise [+-]chiffres[.chiffres]
Function EstNombre(ByVal s As String) As Boolean
    EstNombre = False
    If Len(s) = 0 Then Exit Function
    If Left$(s, 1) = "+" Or Left$(s, 1) = "-" Then s = Mid$(s, 2)
    Dim i As Integer, nDots As Integer, nDigits As Integer, c As String
    For i = 1 To Len(s)
        c = Mid$(s, i, 1)
        If c = "." Then
            nDots = nDots + 1
            If nDots > 1 Then Exit Function
        ElseIf c >= "0" And c <= "9" Then
            nDigits = nDigits + 1
        Else
            Exit Function
        End If
    Next
    EstNombre = (nDigits > 0)
End Function

'------------------------------------------------------------------------------
' Lit l'altitude de la selection courante et charge le CPointRef.
' Renseigne aussi sSep ("." ou ",") et nDec (nb de decimales).
' Retourne False si le texte n'est pas numerique.
Function LireAltitudeTexte(oPoint As CPointRef, _
                            sSep As String, nDec As Integer) As Boolean
    LireAltitudeTexte = False
    oPoint.Invalider

    Dim sBrut As String
    sBrut = g_oSelectionCourante.ValeurTexte
    If InStr(sBrut, ",") > 0 Then
        sSep = ","
        sBrut = Replace(sBrut, ",", ".")
    Else
        sSep = "."
    End If

    If Not EstNombre(sBrut) Then Exit Function

    oPoint.Altitude = Val(sBrut)
    Dim ptOrigine As Point3d
    g_oSelectionCourante.CopierOrigine ptOrigine
    oPoint.DefinirPosition ptOrigine
    oPoint.Valide = True

    Dim nDot As Integer
    nDot = InStrRev(sBrut, ".")
    If nDot > 0 Then nDec = Len(sBrut) - nDot Else nDec = 0

    LireAltitudeTexte = True
End Function

'==============================================================================
' Geometrie de base
'==============================================================================

'------------------------------------------------------------------------------
Function Dist2D(oA As Point3d, oB As Point3d) As Double
    Dist2D = Sqr((oB.X - oA.X) ^ 2 + (oB.Y - oA.Y) ^ 2)
End Function

'------------------------------------------------------------------------------
' Angle en radians depuis l'axe X (sens trigonometrique) pour un vecteur.
Function Angle2D(dDx As Double, dDy As Double) As Double
    If Abs(dDx) < EPSILON And Abs(dDy) < EPSILON Then
        Angle2D = 0#
        Exit Function
    End If
    Angle2D = Atn2Priv(dDy, dDx)
End Function

Private Function Atn2Priv(ByVal dY As Double, ByVal dX As Double) As Double
    If dX > 0 Then
        Atn2Priv = Atn(dY / dX)
    ElseIf dX < 0 Then
        Atn2Priv = Atn(dY / dX) + IIf(dY >= 0, PI, -PI)
    Else
        Atn2Priv = IIf(dY >= 0, PI / 2#, -PI / 2#)
    End If
End Function

'==============================================================================
' Polylignes - abscisses curvilignes
'
' Une polyligne est decrite par ses sommets dX()/dY() (et dZ() en 3D).
' dS() recoit l'abscisse curviligne de chaque sommet (0 au premier).
' La longueur totale developpee est renvoyee.
'==============================================================================

'------------------------------------------------------------------------------
' Abscisses en plan (source 2D : la longueur est mesuree en XY).
Function AbscissesPolyligne2D(dX() As Double, dY() As Double, _
                              dS() As Double) As Double
    Dim nLo As Long, nHi As Long, i As Long
    nLo = LBound(dX): nHi = UBound(dX)
    ReDim dS(nLo To nHi)
    dS(nLo) = 0#
    For i = nLo + 1 To nHi
        dS(i) = dS(i - 1) + Sqr((dX(i) - dX(i - 1)) ^ 2 _
                              + (dY(i) - dY(i - 1)) ^ 2)
    Next
    AbscissesPolyligne2D = dS(nHi)
End Function

'------------------------------------------------------------------------------
' Abscisses sur la geometrie 3D reelle (semis sur element 3D).
Function AbscissesPolyligne3D(dX() As Double, dY() As Double, dZ() As Double, _
                              dS() As Double) As Double
    Dim nLo As Long, nHi As Long, i As Long
    nLo = LBound(dX): nHi = UBound(dX)
    ReDim dS(nLo To nHi)
    dS(nLo) = 0#
    For i = nLo + 1 To nHi
        dS(i) = dS(i - 1) + Sqr((dX(i) - dX(i - 1)) ^ 2 _
                              + (dY(i) - dY(i - 1)) ^ 2 _
                              + (dZ(i) - dZ(i - 1)) ^ 2)
    Next
    AbscissesPolyligne3D = dS(nHi)
End Function

'------------------------------------------------------------------------------
' Point a l'abscisse dAbs sur une polyligne 2D (abscisse bornee a [0, L]).
Sub PointSurPolyligne2D(dX() As Double, dY() As Double, dS() As Double, _
                        ByVal dAbs As Double, _
                        dXOut As Double, dYOut As Double)
    Dim i As Long, dT As Double
    i = TrouverSegment(dS, dAbs, dT)
    dXOut = dX(i - 1) + dT * (dX(i) - dX(i - 1))
    dYOut = dY(i - 1) + dT * (dY(i) - dY(i - 1))
End Sub

'------------------------------------------------------------------------------
' Point a l'abscisse dAbs sur une polyligne 3D.
Sub PointSurPolyligne3D(dX() As Double, dY() As Double, dZ() As Double, _
                        dS() As Double, ByVal dAbs As Double, _
                        dXOut As Double, dYOut As Double, dZOut As Double)
    Dim i As Long, dT As Double
    i = TrouverSegment(dS, dAbs, dT)
    dXOut = dX(i - 1) + dT * (dX(i) - dX(i - 1))
    dYOut = dY(i - 1) + dT * (dY(i) - dY(i - 1))
    dZOut = dZ(i - 1) + dT * (dZ(i) - dZ(i - 1))
End Sub

'------------------------------------------------------------------------------
' Direction unitaire (en plan) du segment porteur de l'abscisse dAbs.
' Sert a orienter un texte le long de l'element. Segment degenere : (1, 0).
Sub TangenteSurPolyligne(dX() As Double, dY() As Double, dS() As Double, _
                         ByVal dAbs As Double, _
                         dDirX As Double, dDirY As Double)
    Dim i As Long, dT As Double, dLen As Double
    i = TrouverSegment(dS, dAbs, dT)
    dDirX = dX(i) - dX(i - 1)
    dDirY = dY(i) - dY(i - 1)
    dLen = Sqr(dDirX * dDirX + dDirY * dDirY)
    If dLen < EPSILON Then
        dDirX = 1#: dDirY = 0#
    Else
        dDirX = dDirX / dLen: dDirY = dDirY / dLen
    End If
End Sub

'------------------------------------------------------------------------------
' Abscisse curviligne du point de la polyligne le plus proche de (dPtX, dPtY).
' Utilise pour placer une altitude intermediaire : la cote cliquee est
' projetee sur l'element pour connaitre son abscisse.
' dDistOut recoit la distance en plan entre le point et sa projection.
Function AbscisseProjetee2D(dX() As Double, dY() As Double, dS() As Double, _
                            ByVal dPtX As Double, ByVal dPtY As Double, _
                            Optional dDistOut As Double) As Double
    Dim nLo As Long, nHi As Long, i As Long
    nLo = LBound(dX): nHi = UBound(dX)

    Dim dBestDist As Double, dBestAbs As Double
    dBestDist = -1#

    For i = nLo + 1 To nHi
        Dim dvx As Double, dvy As Double, dL2 As Double, dT As Double
        dvx = dX(i) - dX(i - 1)
        dvy = dY(i) - dY(i - 1)
        dL2 = dvx * dvx + dvy * dvy
        If dL2 < EPSILON Then
            dT = 0#
        Else
            dT = ((dPtX - dX(i - 1)) * dvx + (dPtY - dY(i - 1)) * dvy) / dL2
            If dT < 0# Then dT = 0#
            If dT > 1# Then dT = 1#
        End If
        Dim dPX As Double, dPY As Double, dD As Double
        dPX = dX(i - 1) + dT * dvx
        dPY = dY(i - 1) + dT * dvy
        dD = Sqr((dPtX - dPX) ^ 2 + (dPtY - dPY) ^ 2)
        If dBestDist < 0# Or dD < dBestDist Then
            dBestDist = dD
            dBestAbs = dS(i - 1) + dT * (dS(i) - dS(i - 1))
        End If
    Next

    dDistOut = dBestDist
    AbscisseProjetee2D = dBestAbs
End Function

'------------------------------------------------------------------------------
' Trouve le segment porteur de l'abscisse dAbs : renvoie l'indice i du sommet
' superieur (le segment est [i-1, i]) et dT la position parametrique 0..1.
' L'abscisse est bornee a [0, longueur totale].
Private Function TrouverSegment(dS() As Double, ByVal dAbs As Double, _
                                dT As Double) As Long
    Dim nLo As Long, nHi As Long, i As Long
    nLo = LBound(dS): nHi = UBound(dS)

    If nHi = nLo Then
        ' Polyligne reduite a un point : segment fictif sur ce point
        TrouverSegment = nHi
        dT = 0#
        Exit Function
    End If

    If dAbs <= dS(nLo) Then
        TrouverSegment = nLo + 1
        dT = 0#
        Exit Function
    End If
    If dAbs >= dS(nHi) Then
        TrouverSegment = nHi
        dT = 1#
        Exit Function
    End If

    For i = nLo + 1 To nHi
        If dAbs <= dS(i) Then
            Dim dLen As Double
            dLen = dS(i) - dS(i - 1)
            If dLen < EPSILON Then dT = 0# Else dT = (dAbs - dS(i - 1)) / dLen
            TrouverSegment = i
            Exit Function
        End If
    Next
    TrouverSegment = nHi
    dT = 1#
End Function

'==============================================================================
' Semis d'abscisses
'==============================================================================

'------------------------------------------------------------------------------
' Mode distance fixe : un point au depart (0), puis tous les dPas, et un point
' a la fin (dLongueur) meme si le dernier intervalle est plus court.
' Renvoie le nombre de points ; dSOut est ReDim 0-based.
Function AbscissesSemisPasFixe(ByVal dLongueur As Double, ByVal dPas As Double, _
                               dSOut() As Double) As Long
    If dLongueur < DIST_MIN Or dPas < DIST_MIN Then
        ReDim dSOut(0 To 0)
        dSOut(0) = 0#
        AbscissesSemisPasFixe = 1
        Exit Function
    End If

    Dim nInter As Long
    nInter = Int(dLongueur / dPas)

    ' Si le reliquat final est negligeable, le dernier multiple EST la fin
    Dim bFinSurPas As Boolean
    bFinSurPas = ((dLongueur - nInter * dPas) < DIST_MIN)

    Dim nNb As Long
    If bFinSurPas Then nNb = nInter + 1 Else nNb = nInter + 2
    ReDim dSOut(0 To nNb - 1)

    Dim i As Long
    For i = 0 To nInter
        dSOut(i) = i * dPas
    Next
    dSOut(nNb - 1) = dLongueur

    AbscissesSemisPasFixe = nNb
End Function

'------------------------------------------------------------------------------
' Mode parts egales : nNombre points repartis uniformement, depart et fin
' inclus (minimum 2). Renvoie le nombre de points ; dSOut est ReDim 0-based.
Function AbscissesSemisPartsEgales(ByVal dLongueur As Double, _
                                   ByVal nNombre As Long, _
                                   dSOut() As Double) As Long
    Dim nNb As Long
    nNb = nNombre
    If nNb < 2 Then nNb = 2
    ReDim dSOut(0 To nNb - 1)

    Dim dPas As Double
    dPas = dLongueur / (nNb - 1)
    Dim i As Long
    For i = 0 To nNb - 1
        dSOut(i) = i * dPas
    Next
    dSOut(nNb - 1) = dLongueur

    AbscissesSemisPartsEgales = nNb
End Function

'==============================================================================
' Altimetrie - interpolation par troncons
'
' Les references (depart, fin, intermediaires) sont des couples
' (abscisse dSRef, altitude dZRef) tries par abscisse croissante.
'==============================================================================

'------------------------------------------------------------------------------
Function InterpolerZ(dZ1 As Double, dZ2 As Double, dT As Double) As Double
    InterpolerZ = dZ1 + (dZ2 - dZ1) * dT
End Function

'------------------------------------------------------------------------------
' Altitude a l'abscisse dAbs : lineaire entre les deux references qui
' l'encadrent, bornee aux altitudes extremes en dehors.
Function InterpolerZTroncons(dSRef() As Double, dZRef() As Double, _
                             ByVal nNbRef As Long, _
                             ByVal dAbs As Double) As Double
    If nNbRef <= 0 Then Exit Function
    If nNbRef = 1 Or dAbs <= dSRef(0) Then
        InterpolerZTroncons = dZRef(0)
        Exit Function
    End If
    If dAbs >= dSRef(nNbRef - 1) Then
        InterpolerZTroncons = dZRef(nNbRef - 1)
        Exit Function
    End If

    Dim i As Long
    For i = 1 To nNbRef - 1
        If dAbs <= dSRef(i) Then
            Dim dLen As Double
            dLen = dSRef(i) - dSRef(i - 1)
            If dLen < DIST_MIN Then
                ' Deux references confondues : on saute au lieu de diviser
                InterpolerZTroncons = dZRef(i)
            Else
                InterpolerZTroncons = dZRef(i - 1) _
                    + (dZRef(i) - dZRef(i - 1)) * (dAbs - dSRef(i - 1)) / dLen
            End If
            Exit Function
        End If
    Next
    InterpolerZTroncons = dZRef(nNbRef - 1)
End Function

'------------------------------------------------------------------------------
' Trie les couples (dSRef, dZRef) par abscisse croissante (tri par insertion :
' les intermediaires sont cliquees dans un ordre quelconque).
Sub TrierRefsParAbscisse(dSRef() As Double, dZRef() As Double, _
                         ByVal nNbRef As Long)
    Dim i As Long, j As Long, dS As Double, dZ As Double
    For i = 1 To nNbRef - 1
        dS = dSRef(i): dZ = dZRef(i)
        j = i - 1
        Do While j >= 0
            If dSRef(j) <= dS Then Exit Do
            dSRef(j + 1) = dSRef(j)
            dZRef(j + 1) = dZRef(j)
            j = j - 1
        Loop
        dSRef(j + 1) = dS
        dZRef(j + 1) = dZ
    Next
End Sub

'------------------------------------------------------------------------------
' Calcule l'altitude de chaque sommet d'une polyligne (abscisses dS) a partir
' des references triees. dZOut est ReDim aux memes bornes que dS.
Sub CalculerZPolyligne(dS() As Double, dSRef() As Double, dZRef() As Double, _
                       ByVal nNbRef As Long, dZOut() As Double)
    Dim nLo As Long, nHi As Long, i As Long
    nLo = LBound(dS): nHi = UBound(dS)
    ReDim dZOut(nLo To nHi)
    For i = nLo To nHi
        dZOut(i) = InterpolerZTroncons(dSRef, dZRef, nNbRef, dS(i))
    Next
End Sub

'------------------------------------------------------------------------------
' Insere dans la polyligne un sommet a chaque abscisse de dSIns qui n'y figure
' pas deja (tolerance DIST_MIN, bornes exclues). Les tableaux dX/dY/dS sont
' reconstruits 0-based. Necessaire avant CalculerZPolyligne : sans sommet a
' l'abscisse d'une reference intermediaire, le changement de pente serait
' perdu (ex. ligne droite de 2 sommets avec un regard au milieu).
Sub InsererAbscisses(dX() As Double, dY() As Double, dS() As Double, _
                     dSIns() As Double, ByVal nNbIns As Long)
    Dim dX0() As Double, dY0() As Double, dS0() As Double
    dX0 = dX: dY0 = dY: dS0 = dS

    Dim nLo As Long, nHi As Long, nNb0 As Long
    nLo = LBound(dS0): nHi = UBound(dS0)
    nNb0 = nHi - nLo + 1
    Dim dLong As Double
    dLong = dS0(nHi)

    Dim dTous() As Double
    ReDim dTous(0 To nNb0 + nNbIns - 1)
    Dim n As Long, i As Long, j As Long
    For i = nLo To nHi
        dTous(i - nLo) = dS0(i)
    Next
    n = nNb0

    For i = 0 To nNbIns - 1
        Dim dV As Double
        dV = dSIns(i)
        If dV > DIST_MIN And dV < dLong - DIST_MIN Then
            Dim bExiste As Boolean
            bExiste = False
            For j = 0 To n - 1
                If Abs(dTous(j) - dV) < DIST_MIN Then
                    bExiste = True
                    Exit For
                End If
            Next
            If Not bExiste Then
                dTous(n) = dV
                n = n + 1
            End If
        End If
    Next

    If n = nNb0 Then Exit Sub   ' rien a inserer

    ' Tri par insertion des abscisses fusionnees
    For i = 1 To n - 1
        Dim dV2 As Double
        dV2 = dTous(i)
        j = i - 1
        Do While j >= 0
            If dTous(j) <= dV2 Then Exit Do
            dTous(j + 1) = dTous(j)
            j = j - 1
        Loop
        dTous(j + 1) = dV2
    Next

    ' Reconstruction de la polyligne sur les abscisses fusionnees
    ReDim dX(0 To n - 1)
    ReDim dY(0 To n - 1)
    ReDim dS(0 To n - 1)
    For i = 0 To n - 1
        Dim dPX As Double, dPY As Double
        PointSurPolyligne2D dX0, dY0, dS0, dTous(i), dPX, dPY
        dX(i) = dPX: dY(i) = dPY
        dS(i) = dTous(i)
    Next
End Sub

'------------------------------------------------------------------------------
' Pente en % sur une longueur developpee. Longueur quasi nulle : 0.
Function PentePctLongueur(ByVal dZ1 As Double, ByVal dZ2 As Double, _
                          ByVal dLongueur As Double) As Double
    If dLongueur < DIST_MIN Then
        PentePctLongueur = 0#
    Else
        PentePctLongueur = (dZ2 - dZ1) / dLongueur * 100#
    End If
End Function

'==============================================================================
' Formatage
'==============================================================================

'------------------------------------------------------------------------------
Function FormatAltitude(dZ As Double, nDec As Integer, sSep As String) As String
    Dim sFmt As String
    If nDec <= 0 Then sFmt = "0" Else sFmt = "0." & String$(nDec, "0")
    Dim sRes As String
    sRes = Format$(dZ, sFmt)
    ' Format$ suit la locale Windows : on normalise puis on applique le separateur
    sRes = Replace(sRes, ",", ".")
    If sSep = "," Then sRes = Replace(sRes, ".", ",")
    FormatAltitude = sRes
End Function

'------------------------------------------------------------------------------
' Formate une pente en pourcentage en valeur absolue.
' nDec facultatif : nombre de decimales, defaut 1.
Function FormatPente(dPente As Double, sSep As String, _
                     Optional nDec As Integer = 1) As String
    Dim sFmt As String
    If nDec <= 0 Then sFmt = "0" Else sFmt = "0." & String$(nDec, "0")
    Dim sRes As String
    sRes = Format$(Abs(dPente), sFmt)
    sRes = Replace(sRes, ",", ".")
    If sSep = "," Then sRes = Replace(sRes, ".", ",")
    FormatPente = sRes & "%"
End Function

Attribute VB_Name = "CGraphique"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CGraphique - Moteur graphique de Trans3D (seule classe qui cree des elements)
'
' Responsabilites :
'   - extraire la geometrie d'un element lineaire en tableaux de sommets,
'     exprimes dans le repere du modele actif (reference 2D ou modele 3D)
'   - creer l'element 3D de la commande Convertir (type conserve si possible,
'     sinon polyligne discretisee)
'   - creer le cercle repere (au Z reel) et le texte altitude (a Z=0.00)
'   - dessiner les apercus dynamiques (Redraw)
'
' Recoit des donnees deja calculees (CCalcul) et des parametres (CSettings).
' Les routines prennent des parametres generiques, jamais l'etat interne
' d'une commande.
'
' TYPES SUPPORTES en extraction :
'   ligne, ligne brisee, courbe (par ses sommets), arc, ellipse/cercle
'   (discretises au pas dPasDiscretisation), B-spline (tentative GetVertices
'   protegee - A VALIDER dans MicroStation, voir ExtraireBspline)
'==============================================================================
Option Explicit

Private Const PI As Double = 3.14159265358979
Private Const NB_SEG_MIN As Long = 8      ' segments mini pour un arc
Private Const NB_SEG_MAX As Long = 2000   ' garde-fou discretisation

'==============================================================================
' Synchronisation des ressources depuis les references 2D
'==============================================================================

'------------------------------------------------------------------------------
' Copie les niveaux et styles de texte des references 2D vers le fichier 3D
' actif. A appeler une fois au lancement de la commande pour que les elements
' crees (textes, cercles, polylignes) puissent utiliser les memes niveaux et
' styles que le fichier source.
Sub SynchroniserRessourcesReferences()
    On Error Resume Next
    Dim oAttachments As Object
    Set oAttachments = ActiveModelReference.Attachments
    If oAttachments Is Nothing Then Exit Sub
    If Err.Number <> 0 Then Err.Clear: Exit Sub

    Dim nCount As Long
    nCount = oAttachments.Count
    If Err.Number <> 0 Then Err.Clear: Exit Sub

    Dim i As Long
    For i = 1 To nCount
        Dim oAtt As Object
        Set oAtt = Nothing
        Set oAtt = oAttachments(i)
        If Not oAtt Is Nothing Then
            SyncNiveauxDepuisRef oAtt
        End If
        Err.Clear
    Next
    On Error GoTo 0
End Sub

'------------------------------------------------------------------------------
Private Sub SyncNiveauxDepuisRef(oAtt As Object)
    On Error Resume Next
    Dim oLevels As Object
    Set oLevels = oAtt.DesignFile.Levels
    If oLevels Is Nothing Then Exit Sub
    If Err.Number <> 0 Then Err.Clear: Exit Sub

    Dim oRefLvl As Level
    For Each oRefLvl In oLevels
        Dim sNom As String
        sNom = oRefLvl.Name
        If Err.Number <> 0 Then Err.Clear: GoTo SuivantNiveau
        If Len(sNom) = 0 Then GoTo SuivantNiveau

        Dim oExist As Level
        Set oExist = Nothing
        Set oExist = ActiveDesignFile.Levels(sNom)
        If oExist Is Nothing Then
            Err.Clear
            ActiveDesignFile.AddNewLevel sNom
            Err.Clear
        End If
SuivantNiveau:
        Err.Clear
    Next
    On Error GoTo 0
End Sub

'==============================================================================
' Extraction de geometrie
'==============================================================================

'------------------------------------------------------------------------------
' Extrait la polyligne d'un element 2D de reference, convertie dans le repere
' du modele actif (oAttachment = Nothing si l'element est du modele actif).
' Renvoie False si le type n'est pas supporte.
Function ExtrairePolyligne2D(oElem As Element, oAttachment As Object, _
                             ByVal dPasDiscret As Double, _
                             dX() As Double, dY() As Double) As Boolean
    Dim aPts() As Point3d
    Dim nNb As Long
    ExtrairePolyligne2D = ExtraireSommets(oElem, dPasDiscret, aPts, nNb)
    If Not ExtrairePolyligne2D Then Exit Function

    ReDim dX(0 To nNb - 1)
    ReDim dY(0 To nNb - 1)
    Dim i As Long, ptM As Point3d
    For i = 0 To nNb - 1
        TransformerPointVersMaitre oAttachment, aPts(i), ptM
        dX(i) = ptM.X
        dY(i) = ptM.Y
    Next
End Function

'------------------------------------------------------------------------------
' Extrait la polyligne 3D d'un element du modele actif (commande Semer).
' Renvoie False si le type n'est pas supporte.
Function ExtrairePolyligne3D(oElem As Element, ByVal dPasDiscret As Double, _
                             dX() As Double, dY() As Double, _
                             dZ() As Double) As Boolean
    Dim aPts() As Point3d
    Dim nNb As Long
    ExtrairePolyligne3D = ExtraireSommets(oElem, dPasDiscret, aPts, nNb)
    If Not ExtrairePolyligne3D Then Exit Function

    ReDim dX(0 To nNb - 1)
    ReDim dY(0 To nNb - 1)
    ReDim dZ(0 To nNb - 1)
    Dim i As Long
    For i = 0 To nNb - 1
        dX(i) = aPts(i).X
        dY(i) = aPts(i).Y
        dZ(i) = aPts(i).Z
    Next
End Function

'------------------------------------------------------------------------------
' Vrai si le type de l'element est convertible par Trans3D.
Function TypeSupporte(oElem As Element) As Boolean
    Select Case oElem.Type
        Case msdElementTypeLine, msdElementTypeLineString, _
             msdElementTypeCurve, msdElementTypeArc, _
             msdElementTypeEllipse, msdElementTypeBsplineCurve
            TypeSupporte = True
        Case Else
            TypeSupporte = False
    End Select
End Function

'------------------------------------------------------------------------------
' Vrai si l'element est ferme (cercle/ellipse complet) : une seule altitude
' de reference suffit (Z constant).
Function EstFerme(oElem As Element) As Boolean
    EstFerme = (oElem.Type = msdElementTypeEllipse)
End Function

'------------------------------------------------------------------------------
' Nom lisible du type d'element (cadre Etat du formulaire).
Function NomType(oElem As Element) As String
    Select Case oElem.Type
        Case msdElementTypeLine:         NomType = "Ligne"
        Case msdElementTypeLineString:   NomType = "Ligne brisee"
        Case msdElementTypeCurve:        NomType = "Courbe"
        Case msdElementTypeArc:          NomType = "Arc"
        Case msdElementTypeEllipse:      NomType = "Cercle/Ellipse"
        Case msdElementTypeBsplineCurve: NomType = "B-spline"
        Case Else:                       NomType = "Type " & oElem.Type
    End Select
End Function

'------------------------------------------------------------------------------
' Sommets bruts de l'element dans son propre repere.
Private Function ExtraireSommets(oElem As Element, ByVal dPasDiscret As Double, _
                                 aPts() As Point3d, nNb As Long) As Boolean
    ExtraireSommets = False
    nNb = 0

    Select Case oElem.Type
        Case msdElementTypeLine, msdElementTypeLineString
            ' LineElement couvre ligne (2 sommets) et ligne brisee
            Dim oLigne As LineElement
            Set oLigne = oElem
            aPts = oLigne.GetVertices
            nNb = UBound(aPts) - LBound(aPts) + 1
            NormaliserBase aPts, nNb
            ExtraireSommets = (nNb >= 2)

        Case msdElementTypeCurve
            ' Courbe (type 11) : passe par ses sommets, utilises tels quels
            Dim oCourbe As CurveElement
            Set oCourbe = oElem
            aPts = oCourbe.GetVertices
            nNb = UBound(aPts) - LBound(aPts) + 1
            NormaliserBase aPts, nNb
            ExtraireSommets = (nNb >= 2)

        Case msdElementTypeArc
            ExtraireSommets = DiscretiserArc(oElem, dPasDiscret, aPts, nNb)

        Case msdElementTypeEllipse
            ExtraireSommets = DiscretiserEllipse(oElem, dPasDiscret, aPts, nNb)

        Case msdElementTypeBsplineCurve
            ExtraireSommets = ExtraireBspline(oElem, aPts, nNb)
    End Select
End Function

'------------------------------------------------------------------------------
' Rebase un tableau de sommets en 0-based si necessaire.
Private Sub NormaliserBase(aPts() As Point3d, ByVal nNb As Long)
    If LBound(aPts) = 0 Then Exit Sub
    Dim aTmp() As Point3d
    ReDim aTmp(0 To nNb - 1)
    Dim i As Long
    For i = 0 To nNb - 1
        aTmp(i) = aPts(LBound(aPts) + i)
    Next
    aPts = aTmp
End Sub

'------------------------------------------------------------------------------
' Discretise un arc au pas donne (angles en radians, repere de l'arc).
Private Function DiscretiserArc(oElem As Element, ByVal dPasDiscret As Double, _
                                aPts() As Point3d, nNb As Long) As Boolean
    DiscretiserArc = False

    Dim oArc As ArcElement
    Set oArc = oElem

    Dim ptC As Point3d, dR1 As Double, dR2 As Double
    Dim dDebut As Double, dBalayage As Double
    Dim oRot As Matrix3d
    On Error GoTo Echec
    ptC = oArc.CenterPoint
    dR1 = oArc.PrimaryRadius
    dR2 = oArc.SecondaryRadius
    dDebut = oArc.StartAngle
    dBalayage = oArc.SweepAngle
    oRot = oArc.Rotation
    On Error GoTo 0

    GenererPointsElliptiques ptC, dR1, dR2, oRot, dDebut, dBalayage, _
                             dPasDiscret, aPts, nNb
    DiscretiserArc = (nNb >= 2)
    Exit Function
Echec:
    DiscretiserArc = False
End Function

'------------------------------------------------------------------------------
' Discretise une ellipse ou un cercle complet (balayage 2*PI, ferme).
Private Function DiscretiserEllipse(oElem As Element, _
                                    ByVal dPasDiscret As Double, _
                                    aPts() As Point3d, nNb As Long) As Boolean
    DiscretiserEllipse = False

    Dim oEll As EllipseElement
    Set oEll = oElem

    Dim ptC As Point3d, dR1 As Double, dR2 As Double
    Dim oRot As Matrix3d
    On Error GoTo Echec
    ptC = oEll.CenterPoint

    dR1 = oEll.PrimaryRadius
    dR2 = oEll.SecondaryRadius
    oRot = oEll.Rotation
    On Error GoTo 0

    GenererPointsElliptiques ptC, dR1, dR2, oRot, 0#, 2# * PI, _
                             dPasDiscret, aPts, nNb
    ' Refermer exactement sur le premier point
    If nNb >= 2 Then aPts(nNb - 1) = aPts(0)
    DiscretiserEllipse = (nNb >= 2)
    Exit Function
Echec:
    DiscretiserEllipse = False
End Function

'------------------------------------------------------------------------------
' Genere les points d'un arc elliptique : local (R1*cos t, R2*sin t, 0),
' monde = centre + Rotation * local (produit fait a la main sur les Row).
Private Sub GenererPointsElliptiques(ptC As Point3d, _
        ByVal dR1 As Double, ByVal dR2 As Double, oRot As Matrix3d, _
        ByVal dDebut As Double, ByVal dBalayage As Double, _
        ByVal dPasDiscret As Double, aPts() As Point3d, nNb As Long)

    ' Nombre de segments d'apres la longueur developpee approchee
    Dim dRMax As Double
    If dR1 > dR2 Then dRMax = dR1 Else dRMax = dR2
    Dim dLongueur As Double
    dLongueur = Abs(dBalayage) * dRMax

    Dim nSeg As Long
    If dPasDiscret > 0.0000001 Then
        nSeg = CLng(dLongueur / dPasDiscret) + 1
    Else
        nSeg = NB_SEG_MIN
    End If
    If nSeg < NB_SEG_MIN Then nSeg = NB_SEG_MIN
    If nSeg > NB_SEG_MAX Then nSeg = NB_SEG_MAX

    nNb = nSeg + 1
    ReDim aPts(0 To nNb - 1)

    Dim i As Long, dT As Double
    Dim vLoc As Point3d, vMonde As Point3d
    For i = 0 To nSeg
        dT = dDebut + dBalayage * CDbl(i) / CDbl(nSeg)
        vLoc.X = dR1 * Cos(dT)
        vLoc.Y = dR2 * Sin(dT)
        vLoc.Z = 0#
        vMonde.X = oRot.RowX.X * vLoc.X + oRot.RowX.Y * vLoc.Y + oRot.RowX.Z * vLoc.Z
        vMonde.Y = oRot.RowY.X * vLoc.X + oRot.RowY.Y * vLoc.Y + oRot.RowY.Z * vLoc.Z
        vMonde.Z = oRot.RowZ.X * vLoc.X + oRot.RowZ.Y * vLoc.Y + oRot.RowZ.Z * vLoc.Z
        aPts(i).X = ptC.X + vMonde.X
        aPts(i).Y = ptC.Y + vMonde.Y
        aPts(i).Z = ptC.Z + vMonde.Z
    Next
End Sub

'------------------------------------------------------------------------------
' B-spline : l'API V8i VBA n'expose pas d'evaluateur documente fiable, et la
' liaison tardive ne sait pas marshaler un tableau de Point3d (UDT).
' Echec propre pour l'instant -> l'etat de commande affichera "type non
' supporte : droppez la B-spline en ligne brisee puis reessayez".
' A EXPLORER sur poste dans MicroStation : BsplineCurve.FromElement puis
' evaluation, ou methodes de BsplineCurveElement visibles dans l'explorateur
' d'objets VBA (F2).
Private Function ExtraireBspline(oElem As Element, _
                                 aPts() As Point3d, nNb As Long) As Boolean
    ExtraireBspline = False
    nNb = 0
End Function

'==============================================================================
' Creation des elements 3D (commande Convertir)
'==============================================================================

'------------------------------------------------------------------------------
' Cree la polyligne 3D (ligne si 2 sommets, ligne brisee sinon) et l'ajoute
' au modele actif. oElemSource peut etre Nothing (symbologie active).
Function CreerPolyligne3D(dX() As Double, dY() As Double, dZ() As Double, _
                          oElemSource As Element, _
                          oSettings As CSettings) As Element
    Dim aPts() As Point3d
    ConstruirePoints dX, dY, dZ, aPts

    Dim oNouv As LineElement
    Set oNouv = CreateLineElement1(Nothing, aPts)
    AppliquerSymbologie oNouv, oElemSource, oSettings
    ActiveModelReference.AddElement oNouv
    Set CreerPolyligne3D = oNouv
End Function

'------------------------------------------------------------------------------
' Arc a Z constant : type natif conserve, pose a l'altitude dZ.
' Renvoie Nothing en cas d'echec (l'appelant discretise alors en polyligne).
Function CreerArc3DZConstant(oArcSource As Element, ByVal dZ As Double, _
                             oAttachment As Object, _
                             oSettings As CSettings) As Element
    Set CreerArc3DZConstant = Nothing

    Dim oArc As ArcElement
    Set oArc = oArcSource

    On Error GoTo Echec
    Dim ptC As Point3d, ptCM As Point3d
    ptC = oArc.CenterPoint
    TransformerPointVersMaitre oAttachment, ptC, ptCM
    ptCM.Z = dZ

    ' Rayons repris tels quels : les coordonnees et dimensions scannees sont
    ' deja compatibles master (le ScaleFactor est une echelle graphique,
    ' cf. TransformerPointVersMaitre dans RechercheAltitude.bas)
    Dim oNouv As ArcElement
    Set oNouv = CreateArcElement2(Nothing, ptCM, _
                    oArc.PrimaryRadius, _
                    oArc.SecondaryRadius, _
                    oArc.Rotation, oArc.StartAngle, oArc.SweepAngle)
    AppliquerSymbologie oNouv, oArcSource, oSettings
    ActiveModelReference.AddElement oNouv
    Set CreerArc3DZConstant = oNouv
    Exit Function
Echec:
    Set CreerArc3DZConstant = Nothing
End Function

'------------------------------------------------------------------------------
' Cercle/ellipse a Z constant : type natif conserve, pose a l'altitude dZ.
' Renvoie Nothing en cas d'echec (l'appelant discretise alors en polyligne).
Function CreerCercle3DZConstant(oEllSource As Element, ByVal dZ As Double, _
                                oAttachment As Object, _
                                oSettings As CSettings) As Element
    Set CreerCercle3DZConstant = Nothing

    Dim oEll As EllipseElement
    Set oEll = oEllSource

    On Error GoTo Echec
    Dim ptC As Point3d
    ptC = oEll.CenterPoint

    Dim ptCM As Point3d
    TransformerPointVersMaitre oAttachment, ptC, ptCM
    ptCM.Z = dZ

    Dim oNouv As EllipseElement
    Set oNouv = CreateEllipseElement2(Nothing, ptCM, _
                    oEll.PrimaryRadius, _
                    oEll.SecondaryRadius, oEll.Rotation)
    AppliquerSymbologie oNouv, oEllSource, oSettings
    ActiveModelReference.AddElement oNouv
    Set CreerCercle3DZConstant = oNouv
    Exit Function
Echec:
    Set CreerCercle3DZConstant = Nothing
End Function

'==============================================================================
' Creation du point cote (commandes Semer et Points)
'==============================================================================

'------------------------------------------------------------------------------
' Cree, selon les bascules de CSettings :
'   - le cercle repere centre en (dXpt, dYpt) au Z reel dZpt
'   - le texte altitude a Z = 0.00 (regle fixe du cahier des charges),
'     decale du rayon du cercle pour rester lisible
' La symbologie (couleur, niveau) est appliquee en mode protege : son echec
' ne doit pas empecher la creation. Un echec de creation leve une erreur
' explicite que l'etat de commande capture et affiche.
Sub CreerPointCote(ByVal dXpt As Double, ByVal dYpt As Double, _
                   ByVal dZpt As Double, _
                   oSettings As CSettings, oCalc As CCalcul)
    On Error Resume Next

    If oSettings.bCreerCercle Then
        Dim ptCercle As Point3d
        ptCercle.X = dXpt: ptCercle.Y = dYpt: ptCercle.Z = dZpt
        Dim oCercle As EllipseElement
        Set oCercle = CreateEllipseElement2(Nothing, ptCercle, _
                          oSettings.oCercle.Rayon, oSettings.oCercle.Rayon, _
                          Matrix3dIdentity())
        If Not oCercle Is Nothing Then
            oCercle.Color = oSettings.oCercle.Couleur
            Set oCercle.Level = ResolverNiveau(oSettings.oCercle.NomNiveau)
            Err.Clear
            ActiveModelReference.AddElement oCercle
        End If
        Err.Clear
    End If

    Dim ptTexte As Point3d
    ptTexte.X = dXpt + oSettings.oCercle.Rayon * 1.5
    ptTexte.Y = dYpt
    If oSettings.bTexteAZero Then
        ptTexte.Z = 0#
    Else
        ptTexte.Z = dZpt
    End If
    Dim oTxt As TextElement
    Set oTxt = ConstruireTexteAltitude(ptTexte, dZpt, oSettings, oCalc)
    If Not oTxt Is Nothing Then
        ActiveModelReference.AddElement oTxt
    End If
    Err.Clear

    On Error GoTo 0
End Sub


'==============================================================================
' Apercus dynamiques (appeles dans IPrimitiveCommandEvents_Dynamics)
'==============================================================================

'------------------------------------------------------------------------------
' Apercu de la polyligne 3D en cours de construction (Convertir).
Sub DessinPolyligneDyn(ByVal DrawMode As MsdDrawingMode, _
                       dX() As Double, dY() As Double, dZ() As Double)
    Dim aPts() As Point3d
    ConstruirePoints dX, dY, dZ, aPts
    On Error Resume Next
    Dim oLigne As LineElement
    Set oLigne = CreateLineElement1(Nothing, aPts)
    oLigne.Color = 4
    oLigne.Redraw DrawMode
    On Error GoTo 0
End Sub

'------------------------------------------------------------------------------
' Surlignage de l'element 2D selectionne a la profondeur du curseur.
Sub DessinSurlignage2D(ByVal DrawMode As MsdDrawingMode, _
                       dX() As Double, dY() As Double, _
                       Optional ByVal dZVue As Double = 0#)
    Dim nLo As Long, nHi As Long, i As Long
    nLo = LBound(dX): nHi = UBound(dX)
    Dim aPts() As Point3d
    ReDim aPts(nLo To nHi)
    For i = nLo To nHi
        aPts(i).X = dX(i)
        aPts(i).Y = dY(i)
        aPts(i).Z = dZVue
    Next
    On Error Resume Next
    Dim oLigne As LineElement
    Set oLigne = CreateLineElement1(Nothing, aPts)
    oLigne.Color = 3
    oLigne.LineWeight = 5
    oLigne.Redraw DrawMode
    On Error GoTo 0
End Sub

'------------------------------------------------------------------------------
' Apercu d'un point cote : cercle au Z reel + texte a Z=0.
Sub DessinPointCoteDyn(ByVal DrawMode As MsdDrawingMode, _
                       ByVal dXpt As Double, ByVal dYpt As Double, _
                       ByVal dZpt As Double, _
                       oSettings As CSettings, oCalc As CCalcul)
    On Error Resume Next

    If oSettings.bCreerCercle Then
        Dim ptCercle As Point3d
        ptCercle.X = dXpt: ptCercle.Y = dYpt: ptCercle.Z = dZpt
        Dim oCercle As EllipseElement
        Set oCercle = CreateEllipseElement2(Nothing, ptCercle, _
                          oSettings.oCercle.Rayon, oSettings.oCercle.Rayon, _
                          Matrix3dIdentity())
        oCercle.Color = oSettings.oCercle.Couleur
        oCercle.Redraw DrawMode
    End If

    Dim ptTexte As Point3d
    ptTexte.X = dXpt + oSettings.oCercle.Rayon * 1.5
    ptTexte.Y = dYpt
    If oSettings.bTexteAZero Then
        ptTexte.Z = 0#
    Else
        ptTexte.Z = dZpt
    End If
    Dim oTxt As TextElement
    Set oTxt = ConstruireTexteAltitude(ptTexte, dZpt, oSettings, oCalc)
    If Not oTxt Is Nothing Then oTxt.Redraw DrawMode

    On Error GoTo 0
End Sub

'------------------------------------------------------------------------------
' Fleche de direction provisoire : indique le sens de parcours de l'element
' depuis son origine. Dessine un segment court + pointe triangulaire.
Sub DessinFlecheDirection(ByVal DrawMode As MsdDrawingMode, _
                          dX() As Double, dY() As Double, _
                          ByVal dTaille As Double)
    On Error Resume Next
    Dim nLo As Long, nHi As Long
    nLo = LBound(dX): nHi = UBound(dX)
    If nHi <= nLo Then Exit Sub

    ' Direction au depart (vers le 2e sommet)
    Dim dDx As Double, dDy As Double, dNorm As Double
    dDx = dX(nLo + 1) - dX(nLo)
    dDy = dY(nLo + 1) - dY(nLo)
    dNorm = Sqr(dDx * dDx + dDy * dDy)
    If dNorm < 0.0001 Then Exit Sub
    dDx = dDx / dNorm: dDy = dDy / dNorm

    ' Hampe : segment de longueur dTaille partant de l'origine
    Dim ptA As Point3d, ptB As Point3d
    ptA.X = dX(nLo): ptA.Y = dY(nLo): ptA.Z = 0#
    ptB.X = ptA.X + dDx * dTaille
    ptB.Y = ptA.Y + dDy * dTaille: ptB.Z = 0#
    Dim oHampe As LineElement
    Set oHampe = CreateLineElement2(Nothing, ptA, ptB)
    oHampe.Color = 1: oHampe.LineWeight = 3
    oHampe.Redraw DrawMode

    ' Pointe : triangle au bout de la hampe
    Dim dFleche As Double
    dFleche = dTaille * 0.4
    Dim aPts(0 To 2) As Point3d
    aPts(0) = ptB
    aPts(1).X = ptB.X - dDx * dFleche + dDy * dFleche * 0.5
    aPts(1).Y = ptB.Y - dDy * dFleche - dDx * dFleche * 0.5
    aPts(1).Z = 0#
    aPts(2).X = ptB.X - dDx * dFleche - dDy * dFleche * 0.5
    aPts(2).Y = ptB.Y - dDy * dFleche + dDx * dFleche * 0.5
    aPts(2).Z = 0#

    Dim oP1 As LineElement, oP2 As LineElement, oP3 As LineElement
    Set oP1 = CreateLineElement2(Nothing, aPts(0), aPts(1))
    Set oP2 = CreateLineElement2(Nothing, aPts(1), aPts(2))
    Set oP3 = CreateLineElement2(Nothing, aPts(2), aPts(0))
    oP1.Color = 1: oP1.LineWeight = 3: oP1.Redraw DrawMode
    oP2.Color = 1: oP2.LineWeight = 3: oP2.Redraw DrawMode
    oP3.Color = 1: oP3.LineWeight = 3: oP3.Redraw DrawMode

    On Error GoTo 0
End Sub

'------------------------------------------------------------------------------
' Croix de reperage (reprise d'InterpolationTopo).
Sub DessinCroix(ByVal DrawMode As MsdDrawingMode, oPt As Point3d, _
                ByVal dTaille As Double)
    Dim oA As Point3d, oB As Point3d, oL As LineElement

    oA.X = oPt.X - dTaille: oA.Y = oPt.Y: oA.Z = oPt.Z
    oB.X = oPt.X + dTaille: oB.Y = oPt.Y: oB.Z = oPt.Z
    Set oL = CreateLineElement2(Nothing, oA, oB)
    oL.Color = 3: oL.Redraw DrawMode

    oA.X = oPt.X: oA.Y = oPt.Y - dTaille
    oB.X = oPt.X: oB.Y = oPt.Y + dTaille
    Set oL = CreateLineElement2(Nothing, oA, oB)
    oL.Color = 3: oL.Redraw DrawMode
End Sub

'==============================================================================
' Utilitaires prives
'==============================================================================

'------------------------------------------------------------------------------
' Construit le texte altitude (sans l'ajouter au modele) : mode duplication
' (texte-modele source) ou mode creation (parametres du formulaire).
Private Function ConstruireTexteAltitude(ptTexte As Point3d, _
        ByVal dZValeur As Double, _
        oSettings As CSettings, oCalc As CCalcul) As TextElement

    Set ConstruireTexteAltitude = Nothing

    Dim sAlt As String
    sAlt = oCalc.FormatAltitude(dZValeur, oSettings.oTexte.Decimales, _
                                oSettings.oTexte.SepDecimal)

    Dim oRot As Matrix3d
    oRot = Matrix3dIdentity()
    On Error Resume Next
    If oSettings.oTexte.CommeModele And Not oSettings.oTextModele Is Nothing Then
        oRot = oSettings.oTextModele.Rotation
    End If
    On Error GoTo 0

    Dim oTxt As TextElement
    Dim bSansModele As Boolean
    bSansModele = True

    On Error Resume Next
    If oSettings.oTexte.CommeModele And Not oSettings.oTextModele Is Nothing Then
        ' PIEGE 5.3 : toujours creer AVEC l'element modele, jamais recopier
        ' TextStyle.Height d'un texte de reference (unites differentes).
        Set oTxt = CreateTextElement1(oSettings.oTextModele, sAlt, ptTexte, oRot)
        If Not oTxt Is Nothing Then bSansModele = False
        Err.Clear
    End If
    If oTxt Is Nothing Then
        Set oTxt = CreateTextElement1(Nothing, sAlt, ptTexte, oRot)
    End If
    On Error GoTo 0
    If oTxt Is Nothing Then Exit Function

    If bSansModele Or Not oSettings.oTexte.CommeModele Then
        ' Mode creation : appliquer les parametres du formulaire
        On Error Resume Next
        Dim oTS As TextStyle
        Set oTS = oTxt.TextStyle
        If oSettings.oTexte.Hauteur > 0 Then oTS.Height = oSettings.oTexte.Hauteur
        If oSettings.oTexte.Largeur > 0 Then
            oTS.Width = oSettings.oTexte.Largeur
        ElseIf oSettings.oTexte.Hauteur > 0 Then
            oTS.Width = oSettings.oTexte.Hauteur
        End If
        If Len(oSettings.oTexte.NomPolice) > 0 Then
            Dim oFont As Object
            Set oFont = FindFont(oSettings.oTexte.NomPolice)
            If Not oFont Is Nothing Then Set oTS.Font = oFont
            Err.Clear
        End If
        If oSettings.oTexte.FondActif Then
            Dim oTSObj As Object
            Set oTSObj = oTS
            oTSObj.Background = True
            Err.Clear
        End If
        oTxt.TextStyle = oTS
        oTxt.Color = oSettings.oTexte.Couleur
        Set oTxt.Level = ResolverNiveau(oSettings.oTexte.NomNiveau)
        Err.Clear
        On Error GoTo 0
    Else
        ' Mode duplication : lier au style nomme du fichier actif (resout le
        ' probleme de fond noir car le style local a le bon BackgroundColor)
        On Error Resume Next
        Dim sStyleNom As String
        sStyleNom = oSettings.oTextModele.TextStyle.Name
        If Err.Number = 0 And Len(sStyleNom) > 0 Then
            Dim oStyleLocal As TextStyle
            Set oStyleLocal = ActiveDesignFile.TextStyles(sStyleNom)
            If Not oStyleLocal Is Nothing Then
                oTxt.TextStyle = oStyleLocal
            End If
        End If
        Err.Clear
        Set oTxt.Level = ResolverNiveau(oSettings.oTexte.NomNiveau)
        Err.Clear
        On Error GoTo 0
    End If

    Set ConstruireTexteAltitude = oTxt
End Function

'------------------------------------------------------------------------------
' Cherche une police par nom. Tout en liaison tardive : l'emplacement exact de
' la collection des polices varie selon les versions (a valider sur poste).
Private Function FindFont(sNom As String) As Object
    Set FindFont = Nothing
    On Error Resume Next
    Dim oApp As Object
    Set oApp = Application
    Dim oFonts As Object
    Set oFonts = oApp.ActiveDesignFile.Fonts
    If oFonts Is Nothing Then
        Err.Clear
        Set oFonts = oApp.Fonts
    End If
    If Not oFonts Is Nothing Then
        Set FindFont = oFonts.Item(sNom)
    End If
    Err.Clear
    On Error GoTo 0
End Function

'------------------------------------------------------------------------------
' Applique niveau/couleur/style/epaisseur de l'element source (mode
' bSymboSource), le niveau etant cree dans le fichier actif s'il n'existe
' pas. Si bSymboSource est faux ou la source Nothing : attributs actifs
' (rien a faire, CreateXxx sans modele les applique deja).
Private Sub AppliquerSymbologie(oDst As Element, oSrc As Element, _
                                oSettings As CSettings)
    If oSrc Is Nothing Then Exit Sub
    If Not oSettings.bSymboSource Then Exit Sub

    On Error Resume Next
    oDst.Color = oSrc.Color: Err.Clear
    oDst.LineWeight = oSrc.LineWeight: Err.Clear
    Set oDst.LineStyle = oSrc.LineStyle: Err.Clear

    Dim sNiveau As String
    sNiveau = oSrc.Level.Name
    If Err.Number = 0 And Len(sNiveau) > 0 Then
        Set oDst.Level = NiveauOuCreation(sNiveau)
    End If
    Err.Clear
    On Error GoTo 0
End Sub

'------------------------------------------------------------------------------
' Niveau par nom dans le fichier actif ; cree s'il n'existe pas (la source
' vient d'une reference dont les niveaux ne sont pas forcement presents).
Private Function NiveauOuCreation(sNiveau As String) As Level
    Set NiveauOuCreation = ActiveSettings.Level

    On Error Resume Next
    Dim oLvl As Level
    Set oLvl = ActiveDesignFile.Levels(sNiveau)
    If oLvl Is Nothing Then
        Err.Clear
        Set oLvl = ActiveDesignFile.AddNewLevel(sNiveau)
    End If
    Err.Clear
    On Error GoTo 0

    If Not oLvl Is Nothing Then Set NiveauOuCreation = oLvl
End Function

'------------------------------------------------------------------------------
' Niveau par nom ou numero ; chaine vide = niveau actif.
' Cree le niveau s'il n'existe pas (meme logique que NiveauOuCreation).
Private Function ResolverNiveau(sNiveau As String) As Level
    Set ResolverNiveau = ActiveSettings.Level
    If sNiveau = "" Then Exit Function

    Dim oLvl As Level
    On Error Resume Next
    Set oLvl = ActiveDesignFile.Levels(sNiveau)
    If oLvl Is Nothing And IsNumeric(sNiveau) Then
        Dim oL As Level
        For Each oL In ActiveDesignFile.Levels
            If oL.Number = CLng(Val(sNiveau)) Then
                Set oLvl = oL: Exit For
            End If
        Next
    End If
    If oLvl Is Nothing Then
        Err.Clear
        Set oLvl = ActiveDesignFile.AddNewLevel(sNiveau)
    End If
    Err.Clear
    On Error GoTo 0
    If Not oLvl Is Nothing Then Set ResolverNiveau = oLvl
End Function

'------------------------------------------------------------------------------
' Assemble trois tableaux de coordonnees en tableau de Point3d.
Private Sub ConstruirePoints(dX() As Double, dY() As Double, dZ() As Double, _
                             aPts() As Point3d)
    Dim nLo As Long, nHi As Long, i As Long
    nLo = LBound(dX): nHi = UBound(dX)
    ReDim aPts(nLo To nHi)
    For i = nLo To nHi
        aPts(i).X = dX(i)
        aPts(i).Y = dY(i)
        aPts(i).Z = dZ(i)
    Next
End Sub

Attribute VB_Name = "CParamSemis"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CParamSemis - Parametres de repartition des points semes (commande Semer)
'
' Deux modes (enum eModeSemis dans Trans3D.bas) :
'   semisDistanceFixe : un point au depart, puis tous les Pas, et un point a
'                       la fin meme si le dernier intervalle est plus court
'   semisPartsEgales  : Nombre de points intermediaires a creer entre depart
'                       et fin (minimum 1)
'
' Simple sac de proprietes, sans dependance a l'API MicroStation.
' Le calcul des abscisses est dans CCalcul (AbscissesSemis*).
'==============================================================================
Option Explicit

Public Mode         As eModeSemis    ' repartition : distance fixe / parts egales
Public Pas          As Double        ' distance fixe entre points (u.m.)
Public Nombre       As Long          ' nombre de points en parts egales

'------------------------------------------------------------------------------
Sub InitDefauts()
    Mode = semisDistanceFixe
    Pas = 0.5
    Nombre = 5
End Sub

Attribute VB_Name = "CPlacerConvertir"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CPlacerConvertir - Machine a etats : conversion d'un element 2D en 3D
'
' Etape 1 (SELECTION) : clic pres de l'element 2D a convertir
'   Data  = selectionner l'element lineaire le plus proche (actif + refs)
'   Reset = quitter la commande
' Etape 2 (Z DEPART) : clic pres de la cote d'altitude de depart
'   (element ferme : cote unique, la creation suit immediatement)
'   Data  = lire la cote (texte/cellule/tag)
'   Reset = revenir a la selection (etape 1)
' Etape 3 (Z FIN) : clic pres de la cote d'altitude de fin
'   Data  = lire la cote
'   Reset = revenir au Z de depart (etape 2)
' Etape 4 (INTERMEDIAIRES) : clics sur les cotes intermediaires (0..N)
'   Data  = ajouter une altitude intermediaire (projetee sur l'element)
'   Reset = CREER l'element 3D puis retour etape 1
'
' L'element cree garde son type natif quand le Z est constant (arc, cercle),
' sinon polyligne 3D avec un sommet insere a chaque altitude intermediaire.
'==============================================================================
Option Explicit

Implements IPrimitiveCommandEvents

Private m_nEtape    As Integer      ' 1..4
Private m_oElem     As Element      ' element 2D selectionne
Private m_oAtt      As Object       ' attachement source (Nothing = modele actif)
Private m_dX()      As Double       ' polyligne extraite (repere modele actif)
Private m_dY()      As Double
Private m_dS()      As Double       ' abscisses curvilignes
Private m_dLong     As Double       ' longueur developpee
Private m_bGeomOk   As Boolean      ' garde : tableaux alloues
Private m_bFerme    As Boolean      ' cercle/ellipse complet : Z constant
Private m_dSRef()   As Double       ' abscisses des altitudes de reference
Private m_dZRef()   As Double       ' altitudes de reference
Private m_nNbRef    As Long

Private Sub IPrimitiveCommandEvents_Start()
    ShowCommand "Trans3D - Convertir"
    RetourSelection
    CommandState.StartDynamics
End Sub

Private Sub IPrimitiveCommandEvents_DataPoint(Point As Point3d, ByVal View As View)
    Select Case m_nEtape
    Case 1
        SelectionnerElement Point

    Case 2
        ' --- Cote de depart (ou cote unique si element ferme) ---
        Dim dAltDep As Double, dPX As Double, dPY As Double
        If Not LireCote(Point, True, dAltDep, dPX, dPY) Then Exit Sub

        AjouterRef 0#, dAltDep
        If m_bFerme Then
            frmTrans3D.AfficherZ "Z = " & FormatZ(dAltDep) & " (constant)"
            CreerElement3DFinal
        Else
            frmTrans3D.AfficherZ "Z dep = " & FormatZ(dAltDep) & _
                                 "   Z fin = -"
            ShowPrompt "Depart Z=" & FormatZ(dAltDep) & _
                       "  |  Cliquez la cote de FIN  (Reset=autre element)"
            m_nEtape = 3
        End If

    Case 3
        ' --- Cote de fin ---
        Dim dAltFin As Double, dFX As Double, dFY As Double
        If Not LireCote(Point, False, dAltFin, dFX, dFY) Then Exit Sub

        AjouterRef m_dLong, dAltFin
        Dim dPente As Double
        dPente = g_oCalc.PentePctLongueur(m_dZRef(0), dAltFin, m_dLong)
        Dim sPente As String
        sPente = g_oCalc.FormatPente(dPente, g_oSettings.oTexte.SepDecimal)
        frmTrans3D.AfficherZ "Z dep = " & FormatZ(m_dZRef(0)) & _
                             "   Z fin = " & FormatZ(dAltFin) & _
                             "   (" & sPente & ")"
        ShowPrompt "Fin Z=" & FormatZ(dAltFin) & "  Pente=" & sPente & _
                   "  |  Data=cote intermediaire  Reset=CREER l'element 3D"
        m_nEtape = 4

    Case 4
        ' --- Altitude intermediaire : projetee sur l'element ---
        Dim dAltInt As Double, dIX As Double, dIY As Double
        If Not LireCote(Point, False, dAltInt, dIX, dIY) Then Exit Sub

        Dim dDist As Double, dAbs As Double
        dAbs = g_oCalc.AbscisseProjetee2D(m_dX, m_dY, m_dS, dIX, dIY, dDist)
        AjouterRef dAbs, dAltInt
        frmTrans3D.AfficherElement g_oMoteur.NomType(m_oElem) & "   L=" & _
                                   Format$(m_dLong, "0.00") & " m   +" & _
                                   (m_nNbRef - 2) & " interm."
        ShowPrompt "Intermediaire " & (m_nNbRef - 2) & " : Z=" & _
                   FormatZ(dAltInt) & " a " & Format$(dAbs, "0.00") & _
                   " m  |  Data=autre cote  Reset=CREER l'element 3D"
    End Select
End Sub

Private Sub IPrimitiveCommandEvents_Dynamics(Point As Point3d, ByVal View As View, _
                                             ByVal DrawMode As MsdDrawingMode)
    If Not m_bGeomOk Then Exit Sub

    ' Surlignage de l'element selectionne a la profondeur du curseur
    g_oMoteur.DessinSurlignage2D DrawMode, m_dX, m_dY, Point.Z

    ' Fleche de direction : indique le sens de parcours (depart -> fin)
    If m_nEtape >= 2 Then
        g_oMoteur.DessinFlecheDirection DrawMode, m_dX, m_dY, _
                                        g_oSettings.dTolTexte * 2
    End If

    ' Apercu de l'element 3D des que depart + fin sont connus
    If m_nEtape = 4 And m_nNbRef >= 2 Then
        Dim dSRefTri() As Double, dZRefTri() As Double
        dSRefTri = m_dSRef: dZRefTri = m_dZRef
        g_oCalc.TrierRefsParAbscisse dSRefTri, dZRefTri, m_nNbRef

        Dim dZ() As Double
        g_oCalc.CalculerZPolyligne m_dS, dSRefTri, dZRefTri, m_nNbRef, dZ
        g_oMoteur.DessinPolyligneDyn DrawMode, m_dX, m_dY, dZ
    End If
End Sub

Private Sub IPrimitiveCommandEvents_Keyin(ByVal Keyin As String)
End Sub

Private Sub IPrimitiveCommandEvents_Reset()
    Select Case m_nEtape
    Case 1
        ' Quitter la commande
        frmTrans3D.Hide
        ShowPrompt "Trans3D - Convertir : termine."
        CommandState.StartDefaultCommand

    Case 2
        RetourSelection

    Case 3
        m_nNbRef = 0
        frmTrans3D.AfficherZ "Z dep = -   Z fin = -"
        ShowPrompt "Cliquez la cote de DEPART  (Reset=autre element)"
        m_nEtape = 2

    Case 4
        CreerElement3DFinal
    End Select
End Sub

Private Sub IPrimitiveCommandEvents_Cleanup()
End Sub

'==============================================================================
' Etapes
'==============================================================================

'------------------------------------------------------------------------------
Private Sub RetourSelection()
    m_nEtape = 1
    m_bGeomOk = False
    m_bFerme = False
    Set m_oElem = Nothing
    Set m_oAtt = Nothing
    m_nNbRef = 0
    frmTrans3D.ReinitialiserEtat
    ShowPrompt "Cliquez pres de l'element 2D a convertir  (Reset=quitter)"
End Sub

'------------------------------------------------------------------------------
Private Sub SelectionnerElement(Point As Point3d)
    If Not TrouverElementProche(Point, g_oSettings.dTolTexte, True, _
                                m_oElem, m_oAtt) Then
        ShowPrompt "Aucun element lineaire a moins de " & _
                   g_oSettings.dTolTexte & " u.m. (B-spline ? droppez-la" & _
                   " en ligne brisee) - recliquez"
        Exit Sub
    End If

    If Not g_oMoteur.ExtrairePolyligne2D(m_oElem, m_oAtt, _
            g_oSettings.dPasDiscretisation, m_dX, m_dY) Then
        ShowPrompt "Type non supporte - recliquez"
        Set m_oElem = Nothing
        Set m_oAtt = Nothing
        Exit Sub
    End If

    m_dLong = g_oCalc.AbscissesPolyligne2D(m_dX, m_dY, m_dS)
    m_bGeomOk = True
    m_bFerme = g_oMoteur.EstFerme(m_oElem)
    m_nNbRef = 0
    ReDim m_dSRef(0 To 15)
    ReDim m_dZRef(0 To 15)
    frmTrans3D.AfficherElement g_oMoteur.NomType(m_oElem) & "   L=" & _
                               Format$(m_dLong, "0.00") & " m"
    frmTrans3D.AfficherZ "Z dep = -   Z fin = -"

    If m_bFerme Then
        ShowPrompt "Element ferme L=" & Format$(m_dLong, "0.00") & _
                   " m  |  Cliquez la cote d'altitude (Z constant)" & _
                   "  (Reset=autre element)"
    Else
        ShowPrompt "Element L=" & Format$(m_dLong, "0.00") & _
                   " m  |  Cliquez la cote de DEPART  (Reset=autre element)"
    End If
    m_nEtape = 2
End Sub

'------------------------------------------------------------------------------
' Creation de l'element 3D d'apres les references saisies, puis retour etape 1.
Private Sub CreerElement3DFinal()
    If m_nNbRef < 1 Then
        RetourSelection
        Exit Sub
    End If

    g_oCalc.TrierRefsParAbscisse m_dSRef, m_dZRef, m_nNbRef

    ' Z constant : toutes les references a la meme altitude
    Dim bZConst As Boolean
    bZConst = True
    Dim i As Long
    For i = 1 To m_nNbRef - 1
        If Abs(m_dZRef(i) - m_dZRef(0)) > 0.0001 Then
            bZConst = False
            Exit For
        End If
    Next

    ' Type natif conserve si possible (arc/cercle a Z constant)
    Dim oNouv As Element
    Set oNouv = Nothing
    If bZConst Then
        Select Case m_oElem.Type
            Case msdElementTypeArc
                Set oNouv = g_oMoteur.CreerArc3DZConstant(m_oElem, _
                                m_dZRef(0), m_oAtt, g_oSettings)
            Case msdElementTypeEllipse
                Set oNouv = g_oMoteur.CreerCercle3DZConstant(m_oElem, _
                                m_dZRef(0), m_oAtt, g_oSettings)
        End Select
    End If

    ' Sinon : polyligne 3D, avec un sommet a chaque altitude intermediaire
    If oNouv Is Nothing Then
        If m_nNbRef > 2 Then
            g_oCalc.InsererAbscisses m_dX, m_dY, m_dS, m_dSRef, m_nNbRef
        End If
        Dim dZ() As Double
        g_oCalc.CalculerZPolyligne m_dS, m_dSRef, m_dZRef, m_nNbRef, dZ
        Set oNouv = g_oMoteur.CreerPolyligne3D(m_dX, m_dY, dZ, m_oElem, _
                                               g_oSettings)
    End If

    ' Points cotes aux extremites (cercle au Z reel + texte)
    Dim nDep As Long, nFin As Long
    nDep = LBound(m_dX): nFin = UBound(m_dX)
    On Error Resume Next
    g_oMoteur.CreerPointCote m_dX(nDep), m_dY(nDep), _
                             m_dZRef(0), g_oSettings, g_oCalc
    Err.Clear
    If Not m_bFerme And m_nNbRef >= 2 Then
        g_oMoteur.CreerPointCote m_dX(nFin), m_dY(nFin), _
                                 m_dZRef(m_nNbRef - 1), g_oSettings, g_oCalc
        Err.Clear
    End If

    ' Decoupage : points intermediaires le long de l'element
    If g_oSettings.bDecoupage And Not m_bFerme Then
        Dim dS3D() As Double, dZ3D() As Double
        ReDim dZ3D(nDep To nFin)
        If bZConst Then
            Dim k As Long
            For k = nDep To nFin: dZ3D(k) = m_dZRef(0): Next
        Else
            Dim j As Long
            For j = nDep To nFin: dZ3D(j) = dZ(j): Next
        End If
        Dim dLong3D As Double
        dLong3D = g_oCalc.AbscissesPolyligne3D(m_dX, m_dY, dZ3D, dS3D)

        Dim dSemis() As Double, nNbSemis As Long
        If g_oSettings.oSemis.Mode = semisPartsEgales Then
            nNbSemis = g_oCalc.AbscissesSemisPartsEgales(dLong3D, _
                           g_oSettings.oSemis.Nombre + 2, dSemis)
        Else
            nNbSemis = g_oCalc.AbscissesSemisPasFixe(dLong3D, _
                           g_oSettings.oSemis.Pas, dSemis)
        End If

        Dim iSe As Long
        Dim dPX As Double, dPY As Double, dPZ As Double
        For iSe = 1 To nNbSemis - 2
            g_oCalc.PointSurPolyligne3D m_dX, m_dY, dZ3D, dS3D, dSemis(iSe), dPX, dPY, dPZ
            Err.Clear
            g_oMoteur.CreerPointCote dPX, dPY, dPZ, g_oSettings, g_oCalc
            Err.Clear
        Next
    End If
    On Error GoTo 0

    Dim sBilan As String
    If bZConst Then
        sBilan = "Element 3D cree a Z=" & FormatZ(m_dZRef(0))
    Else
        Dim dPente As Double
        dPente = g_oCalc.PentePctLongueur(m_dZRef(0), m_dZRef(m_nNbRef - 1), _
                                          m_dLong)
        sBilan = "Element 3D cree (pente moy. " & _
                 g_oCalc.FormatPente(dPente, g_oSettings.oTexte.SepDecimal) & ")"
    End If
    ShowPrompt sBilan & "  |  Cliquez le prochain element  (Reset=quitter)"

    RetourSelection
    frmTrans3D.AfficherElement sBilan
End Sub

'==============================================================================
' Utilitaires prives
'==============================================================================

'------------------------------------------------------------------------------
' Lit la cote la plus proche du clic. bChargerModele : memorise le texte
' source comme modele de style (fait sur la cote de depart).
' Renvoie l'altitude et la position de la cote (repere du modele actif).
Private Function LireCote(Point As Point3d, ByVal bChargerModele As Boolean, _
                          dAlt As Double, dPosX As Double, _
                          dPosY As Double) As Boolean
    LireCote = False

    Dim oText As TextElement
    If Not TrouverAltitudeProche(Point, g_oSettings.dTolTexte, oText) Then
        ShowPrompt "Aucune cote a moins de " & g_oSettings.dTolTexte & _
                   " u.m. - recliquez"
        Exit Function
    End If

    Dim oCote As New CPointRef
    Dim sSep As String, nDec As Integer
    If Not g_oCalc.LireAltitudeTexte(oCote, sSep, nDec) Then
        ShowPrompt "Texte '" & g_oSelectionCourante.ValeurTexte & _
                   "' non numerique - recliquez"
        Exit Function
    End If

    If bChargerModele Then
        If Not oText Is Nothing Then
            g_oSettings.ChargerModeleTexte oText, sSep, nDec
        ElseIf Not g_oSelectionCourante.oTag Is Nothing Then
            g_oSettings.ChargerModeleDepuisTag g_oSelectionCourante.oTag, _
                                               sSep, nDec
        Else
            g_oSettings.oTexte.SepDecimal = sSep
            g_oSettings.AjusterDecimales nDec
        End If
        frmTrans3D.RafraichirTexte
    Else
        g_oSettings.AjusterDecimales nDec
    End If

    dAlt = oCote.Altitude
    dPosX = oCote.X
    dPosY = oCote.Y
    LireCote = True
End Function

'------------------------------------------------------------------------------
Private Sub AjouterRef(ByVal dAbs As Double, ByVal dZ As Double)
    If m_nNbRef > UBound(m_dSRef) Then
        ReDim Preserve m_dSRef(0 To UBound(m_dSRef) + 8)
        ReDim Preserve m_dZRef(0 To UBound(m_dZRef) + 8)
    End If
    m_dSRef(m_nNbRef) = dAbs
    m_dZRef(m_nNbRef) = dZ
    m_nNbRef = m_nNbRef + 1
End Sub

'------------------------------------------------------------------------------
Private Function FormatZ(ByVal dZ As Double) As String
    FormatZ = g_oCalc.FormatAltitude(dZ, g_oSettings.oTexte.Decimales, _
                                     g_oSettings.oTexte.SepDecimal)
End Function

Attribute VB_Name = "CPlacerPoints"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CPlacerPoints - Machine a etats : point 3D depuis une position 2D + une cote
'
' Etape 1 (POSITION) : snap de la position XY exacte du point
'   Data  = memoriser le XY snappe (sommet, intersection...)
'   Reset = quitter la commande
' Etape 2 (ALTITUDE) : clic pres de la cote d'altitude (texte/cellule/tag)
'   Data  = lire la cote, creer le point cote (cercle au Z reel + texte a
'           Z=0.00), retour etape 1
'   Reset = abandonner cette position, retour etape 1
'
' REGLE : le Z du point snappe n'est JAMAIS utilise - seule la valeur de la
' cote fournit l'altitude (le snap renvoie le Z de l'element vise).
'==============================================================================
Option Explicit

Implements IPrimitiveCommandEvents

Private m_nEtape    As Integer      ' 1..2
Private m_dPosX     As Double       ' position XY memorisee (repere actif)
Private m_dPosY     As Double

Private Sub IPrimitiveCommandEvents_Start()
    ShowCommand "Trans3D - Points"
    RetourPosition
    CommandState.StartDynamics
End Sub

Private Sub IPrimitiveCommandEvents_DataPoint(Point As Point3d, ByVal View As View)
    Select Case m_nEtape
    Case 1
        ' --- Memoriser la position (le Z snappe est ignore) ---
        m_dPosX = Point.X
        m_dPosY = Point.Y
        frmTrans3D.AfficherElement "Position fixee (" & _
            Format$(m_dPosX, "0.00") & " ; " & Format$(m_dPosY, "0.00") & ")"
        ShowPrompt "Position fixee  |  Cliquez la cote d'altitude" & _
                   "  (Reset=autre position)"
        m_nEtape = 2

    Case 2
        ' --- Lire la cote et creer le point ---
        Dim oText As TextElement
        If Not TrouverAltitudeProche(Point, g_oSettings.dTolTexte, oText) Then
            ShowPrompt "Aucune cote a moins de " & g_oSettings.dTolTexte & _
                       " u.m. - recliquez"
            Exit Sub
        End If

        Dim oCote As New CPointRef
        Dim sSep As String, nDec As Integer
        If Not g_oCalc.LireAltitudeTexte(oCote, sSep, nDec) Then
            ShowPrompt "Texte '" & g_oSelectionCourante.ValeurTexte & _
                       "' non numerique - recliquez"
            Exit Sub
        End If

        ' La cote lue sert de modele de style pour le texte cree
        If Not oText Is Nothing Then
            g_oSettings.ChargerModeleTexte oText, sSep, nDec
        ElseIf Not g_oSelectionCourante.oTag Is Nothing Then
            g_oSettings.ChargerModeleDepuisTag g_oSelectionCourante.oTag, _
                                               sSep, nDec
        Else
            g_oSettings.oTexte.SepDecimal = sSep
            g_oSettings.AjusterDecimales nDec
        End If
        frmTrans3D.RafraichirTexte

        ' Les erreurs des evenements de commande sont avalees par V8i sans
        ' dialogue : on les capture pour les afficher au lieu d'echouer muet.
        Dim sErreur As String
        On Error Resume Next
        g_oMoteur.CreerPointCote m_dPosX, m_dPosY, oCote.Altitude, _
                                 g_oSettings, g_oCalc
        If Err.Number <> 0 Then _
            sErreur = "(" & Err.Number & ") " & Err.Description
        On Error GoTo 0

        If Len(sErreur) > 0 Then
            ShowPrompt "ERREUR creation : " & sErreur
            frmTrans3D.AfficherZ "ERREUR : " & sErreur
            Exit Sub
        End If

        Dim sZ As String
        sZ = g_oCalc.FormatAltitude(oCote.Altitude, _
                 g_oSettings.oTexte.Decimales, g_oSettings.oTexte.SepDecimal)
        frmTrans3D.AfficherZ "Dernier point : Z = " & sZ
        ShowPrompt "Point cree Z=" & sZ & _
                   "  |  Snappez la position suivante  (Reset=quitter)"
        RetourPosition
    End Select
End Sub

Private Sub IPrimitiveCommandEvents_Dynamics(Point As Point3d, ByVal View As View, _
                                             ByVal DrawMode As MsdDrawingMode)
    If m_nEtape <> 2 Then Exit Sub

    ' Croix sur la position memorisee (a plat : l'altitude n'est pas connue)
    Dim ptPos As Point3d
    ptPos.X = m_dPosX
    ptPos.Y = m_dPosY
    ptPos.Z = 0#
    g_oMoteur.DessinCroix DrawMode, ptPos, g_oSettings.oCercle.Rayon
End Sub

Private Sub IPrimitiveCommandEvents_Keyin(ByVal Keyin As String)
End Sub

Private Sub IPrimitiveCommandEvents_Reset()
    Select Case m_nEtape
    Case 1
        frmTrans3D.Hide
        ShowPrompt "Trans3D - Points : termine."
        CommandState.StartDefaultCommand

    Case 2
        RetourPosition
    End Select
End Sub

Private Sub IPrimitiveCommandEvents_Cleanup()
End Sub

'------------------------------------------------------------------------------
Private Sub RetourPosition()
    m_nEtape = 1
    ShowPrompt "Snappez la position du point 3D  (Reset=quitter)"
End Sub

Attribute VB_Name = "CPlacerSemis"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CPlacerSemis - Machine a etats : semis de points cotes sur un element 3D
'
' Etape 1 (SELECTION) : clic pres de l'element 3D du modele actif
'   Data  = selectionner l'element lineaire le plus proche, extraire sa
'           geometrie 3D reelle
'   Reset = quitter la commande
' Etape 2 (APERCU/CREATION) : apercu du semis complet
'   Dynamics = apercu des points semes selon les parametres courants du
'              formulaire (pas fixe ou parts egales, modifiables en direct)
'   Data  = creer tous les points cotes (cercle au Z reel + texte a Z=0),
'           retour etape 1
'   Reset = abandonner cet element, retour etape 1
'
' Le Z de chaque point est interpole sur la geometrie 3D de l'element.
'==============================================================================
Option Explicit

Implements IPrimitiveCommandEvents

Private m_nEtape    As Integer      ' 1..2
Private m_oElem     As Element      ' element 3D selectionne
Private m_dX()      As Double       ' polyligne 3D extraite
Private m_dY()      As Double
Private m_dZ()      As Double
Private m_dS()      As Double       ' abscisses curvilignes 3D
Private m_dLong     As Double       ' longueur developpee 3D
Private m_bGeomOk   As Boolean      ' garde : tableaux alloues

Private Sub IPrimitiveCommandEvents_Start()
    ShowCommand "Trans3D - Semer"
    RetourSelection
    CommandState.StartDynamics
End Sub

Private Sub IPrimitiveCommandEvents_DataPoint(Point As Point3d, ByVal View As View)
    Select Case m_nEtape
    Case 1
        SelectionnerElement Point

    Case 2
        ' --- Creer tous les points cotes du semis ---
        Dim dSemis() As Double, nNb As Long
        nNb = CalculerSemis(dSemis)
        If nNb < 1 Then
            ShowPrompt "Parametres de semis invalides - verifiez le formulaire"
            Exit Sub
        End If

        ' Les erreurs des evenements de commande sont avalees par V8i sans
        ' dialogue : on les capture pour les afficher au lieu d'echouer muet.
        Dim i As Long, nCrees As Long
        Dim dPX As Double, dPY As Double, dPZ As Double
        Dim sErreur As String
        nCrees = 0
        On Error Resume Next
        For i = 0 To nNb - 1
            g_oCalc.PointSurPolyligne3D m_dX, m_dY, m_dZ, m_dS, dSemis(i), _
                                        dPX, dPY, dPZ
            If Err.Number <> 0 Then
                sErreur = "calcul (" & Err.Number & ") " & Err.Description
                Exit For
            End If
            g_oMoteur.CreerPointCote dPX, dPY, dPZ, g_oSettings, g_oCalc
            If Err.Number <> 0 Then
                sErreur = "(" & Err.Number & ") " & Err.Description
                Exit For
            End If
            nCrees = nCrees + 1
        Next
        On Error GoTo 0

        If Len(sErreur) > 0 Then
            ShowPrompt "ERREUR apres " & nCrees & "/" & nNb & _
                       " points : " & sErreur
            frmTrans3D.AfficherZ "ERREUR : " & sErreur
            Exit Sub
        End If

        ShowPrompt nCrees & " points crees  |  Cliquez le prochain element" & _
                   "  (Reset=quitter)"
        RetourSelection
        frmTrans3D.AfficherElement nCrees & " points crees"
    End Select
End Sub

Private Sub IPrimitiveCommandEvents_Dynamics(Point As Point3d, ByVal View As View, _
                                             ByVal DrawMode As MsdDrawingMode)
    If m_nEtape <> 2 Or Not m_bGeomOk Then Exit Sub

    Dim dSemis() As Double, nNb As Long
    nNb = CalculerSemis(dSemis)
    If nNb < 1 Then Exit Sub

    Dim i As Long
    Dim dPX As Double, dPY As Double, dPZ As Double
    For i = 0 To nNb - 1
        g_oCalc.PointSurPolyligne3D m_dX, m_dY, m_dZ, m_dS, dSemis(i), _
                                    dPX, dPY, dPZ
        g_oMoteur.DessinPointCoteDyn DrawMode, dPX, dPY, dPZ, _
                                     g_oSettings, g_oCalc
    Next

    ShowPrompt "Semis : " & nNb & " points sur " & _
               Format$(m_dLong, "0.00") & " m  (Data=creer  Reset=abandonner)"
End Sub

Private Sub IPrimitiveCommandEvents_Keyin(ByVal Keyin As String)
End Sub

Private Sub IPrimitiveCommandEvents_Reset()
    Select Case m_nEtape
    Case 1
        frmTrans3D.Hide
        ShowPrompt "Trans3D - Semer : termine."
        CommandState.StartDefaultCommand

    Case 2
        RetourSelection
    End Select
End Sub

Private Sub IPrimitiveCommandEvents_Cleanup()
End Sub

'==============================================================================
' Etapes et utilitaires prives
'==============================================================================

'------------------------------------------------------------------------------
Private Sub RetourSelection()
    m_nEtape = 1
    m_bGeomOk = False
    Set m_oElem = Nothing
    frmTrans3D.ReinitialiserEtat
    ShowPrompt "Cliquez pres de l'element 3D a coter  (Reset=quitter)"
End Sub

'------------------------------------------------------------------------------
Private Sub SelectionnerElement(Point As Point3d)
    Dim oAtt As Object
    If Not TrouverElementProche(Point, g_oSettings.dTolTexte, False, _
                                m_oElem, oAtt) Then
        ShowPrompt "Aucun element lineaire du modele actif a moins de " & _
                   g_oSettings.dTolTexte & " u.m. - recliquez"
        Exit Sub
    End If

    If Not g_oMoteur.ExtrairePolyligne3D(m_oElem, _
            g_oSettings.dPasDiscretisation, m_dX, m_dY, m_dZ) Then
        ShowPrompt "Type non supporte - recliquez"
        Set m_oElem = Nothing
        Exit Sub
    End If

    m_dLong = g_oCalc.AbscissesPolyligne3D(m_dX, m_dY, m_dZ, m_dS)
    m_bGeomOk = True

    On Error Resume Next
    m_oElem.Redraw msdDrawingModeHilite
    On Error GoTo 0

    frmTrans3D.AfficherElement g_oMoteur.NomType(m_oElem) & "   L=" & _
                               Format$(m_dLong, "0.00") & " m"
    frmTrans3D.AfficherZ "Z dep = " & FormatZ(m_dZ(LBound(m_dZ))) & _
                         "   Z fin = " & FormatZ(m_dZ(UBound(m_dZ)))
    ShowPrompt "Element L=" & Format$(m_dLong, "0.00") & _
               " m  |  Data=creer le semis  Reset=abandonner"
    m_nEtape = 2
End Sub

'------------------------------------------------------------------------------
Private Function FormatZ(ByVal dZ As Double) As String
    FormatZ = g_oCalc.FormatAltitude(dZ, g_oSettings.oTexte.Decimales, _
                                     g_oSettings.oTexte.SepDecimal)
End Function

'------------------------------------------------------------------------------
' Abscisses du semis selon les parametres courants (relus a chaque appel :
' le formulaire modeless peut les changer pendant l'apercu).
Private Function CalculerSemis(dSemis() As Double) As Long
    If g_oSettings.oSemis.Mode = semisPartsEgales Then
        CalculerSemis = g_oCalc.AbscissesSemisPartsEgales(m_dLong, _
                            g_oSettings.oSemis.Nombre, dSemis)
    Else
        CalculerSemis = g_oCalc.AbscissesSemisPasFixe(m_dLong, _
                            g_oSettings.oSemis.Pas, dSemis)
    End If
End Function

Attribute VB_Name = "CPointRef"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CPointRef - Point de reference topographique (P1 ou P2)
'
' Contient les donnees geometriques et altimetriques d un point connu.
'
' NOTE VBA : un membre Public de type UDT (Point3d) est interdit dans un
' module de classe (erreur de compilation). Les coordonnees sont donc
' stockees en trois Double ; la conversion vers Point3d se fait par des Sub
' avec parametre de sortie (jamais de retour UDT sur ce poste).
'
' Le parsing du texte est delegue a CCalcul.
'==============================================================================
Option Explicit

Public X            As Double   ' coordonnees du point (origin du texte)
Public Y            As Double
Public Z            As Double
Public Altitude     As Double   ' altitude numerique
Public Valide       As Boolean  ' True si le point a ete correctement charge

'------------------------------------------------------------------------------
Sub Invalider()
    Valide = False
    Altitude = 0#
End Sub

'------------------------------------------------------------------------------
' Charge la position depuis un Point3d (ex. origin du texte)
Sub DefinirPosition(oPt As Point3d)
    X = oPt.X: Y = oPt.Y: Z = oPt.Z
End Sub

'------------------------------------------------------------------------------
' Copie la position dans le Point3d fourni par l'appelant
Sub CopierPosition(oPt As Point3d)
    oPt.X = X: oPt.Y = Y: oPt.Z = Z
End Sub

Attribute VB_Name = "CSettings"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CSettings - Parametres partages des trois commandes Trans3D
'
' Agregateur unique des parametres, regroupes par domaine :
'   oTexte   : symbologie et format du texte altitude (duplication / creation)
'   oCercle  : symbologie du cercle repere
'   oSemis   : repartition des points semes (Semer)
'
' Regles fixes (cahier des charges, spec section 1) :
'   - le cercle repere est cree au Z reel calcule (c'est le point exploitable
'     pour la modelisation)
'   - le texte altitude est cree a Z = 0.00 (lecture propre en vue top, pas de
'     surcharge du modele 3D)
'   - le Z d'un point snappe n'est jamais utilise comme altitude
'
' Instancie une seule fois dans Trans3D.bas (g_oSettings), passe en parametre
' aux classes qui en ont besoin (CGraphique, etats de commande, formulaire).
'==============================================================================
Option Explicit

Public oTexte           As CSymboTexte      ' symbologie et format du texte
Public oCercle          As CSymboCercle     ' symbologie du cercle repere
Public oSemis           As CParamSemis      ' repartition des points semes

Public bTexteAZero      As Boolean          ' Semer/Points : texte a Z=0.00 (sinon Z reel)
Public bCreerCercle     As Boolean          ' Semer/Points : creer le cercle repere

Public bSymboSource     As Boolean          ' Convertir : True = dupliquer la
                                            ' symbologie de l'element 2D source,
                                            ' False = attributs actifs
Public bDecoupage       As Boolean          ' Convertir : creer des points intermediaires
Public dPasDiscretisation As Double         ' Convertir : pas de discretisation
                                            ' des arcs/courbes/B-splines pentus (u.m.)

Public dTolTexte        As Double           ' rayon de recherche des cotes autour du clic (u.m.)

Public oTextModele      As TextElement      ' texte source : modele pour CreateTextElement1
Public oTagModele       As TagElement       ' tag source : modele quand la cote est un tag
Public dModeleHauteur   As Double           ' hauteur du texte source (0 = non defini)

'------------------------------------------------------------------------------
Sub Init()
    Set oTexte = New CSymboTexte
    oTexte.InitDefauts
    Set oCercle = New CSymboCercle
    oCercle.InitDefauts
    Set oSemis = New CParamSemis
    oSemis.InitDefauts

    bTexteAZero = False
    bCreerCercle = True
    bSymboSource = True
    bDecoupage = False
    dPasDiscretisation = 0.5
    dTolTexte = 1#

    Set oTextModele = Nothing
    Set oTagModele = Nothing
    dModeleHauteur = 0#
End Sub

'------------------------------------------------------------------------------
' Appele apres la lecture d'une cote texte : memorise le texte-modele et ses
' attributs pour les creations en mode duplication.
' PIEGE 5.3 : la hauteur est lue sur un element cree AVEC modele, jamais sur
' TextStyle.Height du texte de la reference (unites potentiellement
' differentes : texte 100 a 1000 fois trop grand sinon).
Sub ChargerModeleTexte(oText As TextElement, sSep As String, nDec As Integer)
    Set oTextModele = oText
    Set oTagModele = Nothing
    oTexte.ChargerDepuisElement oText
    oTexte.SepDecimal = sSep
    AjusterDecimales nDec

    On Error Resume Next
    Dim oTemp As TextElement
    Dim ptO As Point3d
    Set oTemp = CreateTextElement1(oText, "0", ptO, Matrix3dIdentity())
    If Not oTemp Is Nothing Then
        dModeleHauteur = CDbl(oTemp.TextStyle.Height)
    Else
        Err.Clear
        dModeleHauteur = CDbl(oText.TextStyle.Height)
    End If
    If Err.Number <> 0 Then dModeleHauteur = 0#
    Err.Clear

    SyncStyleTexteModele oText
    Err.Clear
    On Error GoTo 0
End Sub

'------------------------------------------------------------------------------
' Cree le style de texte du modele dans le fichier actif s'il n'existe pas.
' Le background est active en deux temps pour que MicroStation initialise
' correctement la couleur de fond (comme un toggle manuel dans la UI).
Private Sub SyncStyleTexteModele(oText As TextElement)
    On Error Resume Next
    Dim oSrcTS As TextStyle
    Set oSrcTS = oText.TextStyle
    If oSrcTS Is Nothing Then Exit Sub

    Dim sNom As String
    sNom = oSrcTS.Name
    If Err.Number <> 0 Or Len(sNom) = 0 Then Err.Clear: Exit Sub

    Dim oExist As TextStyle
    Set oExist = Nothing
    Set oExist = ActiveDesignFile.TextStyles(sNom)
    If Not oExist Is Nothing Then Err.Clear: Exit Sub

    Err.Clear
    Dim oNew As TextStyle
    Set oNew = ActiveDesignFile.TextStyles.Add(Nothing, sNom)
    If oNew Is Nothing Then Err.Clear: Exit Sub

    oNew.Height = oSrcTS.Height
    oNew.Width = oSrcTS.Width
    Set oNew.Font = oSrcTS.Font
    oNew.Color = oSrcTS.Color

    Dim oNewObj As Object, oSrcObj As Object
    Set oNewObj = oNew
    Set oSrcObj = oSrcTS

    ' Tester si la source a un background actif
    Dim bSrcBg As Boolean
    bSrcBg = False
    bSrcBg = CBool(oSrcObj.Background)
    Err.Clear

    If bSrcBg Then
        ' Etape 1 : creer sans background (etat initial propre)
        oNewObj.Background = False
        Err.Clear
        ' Etape 2 : activer le background (MicroStation initialise le fill)
        oNewObj.Background = True
        Err.Clear
    End If

    Err.Clear
    On Error GoTo 0
End Sub

'------------------------------------------------------------------------------
' Appele quand la cote lue est un tag : estime la hauteur depuis le Range.
Sub ChargerModeleDepuisTag(oTag As TagElement, sSep As String, nDec As Integer)
    Set oTagModele = oTag
    oTexte.SepDecimal = sSep
    AjusterDecimales nDec
    dModeleHauteur = 0#

    On Error Resume Next
    Dim oRng As Range3d
    oRng = oTag.Range
    Dim ptL As Point3d, ptH As Point3d
    ptL = oRng.Low: ptH = oRng.High
    Dim dHY As Double, dHX As Double
    dHY = Abs(ptH.Y - ptL.Y)
    dHX = Abs(ptH.X - ptL.X)
    If dHY > 0 And dHX > 0 Then
        If dHX < dHY Then dModeleHauteur = dHX Else dModeleHauteur = dHY
    End If
    Err.Clear
    On Error GoTo 0
End Sub

'------------------------------------------------------------------------------
' En mode duplication, conserve le plus grand nombre de decimales rencontre
' sur les cotes sources. En mode creation, les decimales du formulaire priment.
Sub AjusterDecimales(nDec As Integer)
    If Not oTexte.CommeModele Then Exit Sub
    If nDec > oTexte.Decimales Then oTexte.Decimales = nDec
End Sub

'------------------------------------------------------------------------------
' Vrai si un texte-modele est disponible (une cote texte a ete lue)
Property Get TextModeleDisponible() As Boolean
    TextModeleDisponible = Not (oTextModele Is Nothing)
End Property

Attribute VB_Name = "CSymboCercle"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CSymboCercle - Attributs de symbologie du cercle topo
'
' Configures par l'utilisateur via frmInterpolation (Tool Settings).
' Persistent pendant toute la duree de la commande.
'==============================================================================
Option Explicit

Public Rayon        As Double   ' demi-diametre en unites maitre
Public Couleur      As Long     ' index couleur MicroStation 0-255
Public NomNiveau    As String   ' "" = meme niveau que le texte P1

'------------------------------------------------------------------------------
' Valeurs par defaut au demarrage de la commande
Sub InitDefauts()
    Rayon = 0.075    ' diametre = 0.10
    Couleur = 2     ' vert
    NomNiveau = ""  ' niveau du texte P1
End Sub

'------------------------------------------------------------------------------
' Diametre (propriete calculee pour l'affichage dans le formulaire)
Property Get Diametre() As Double
    Diametre = Rayon * 2#
End Property

Property Let Diametre(dDiam As Double)
    Rayon = dDiam / 2#
End Property

Attribute VB_Name = "CSymboTexte"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CSymboTexte - Attributs de symbologie du texte altitude
'
' Deux modes, communs a toutes les commandes Trans3D (reglage global) :
'   CommeModele = True (defaut, mode duplication) : le texte cree reprend
'     tous les attributs du texte source lu sur la reference (via
'     CreateTextElement1 avec modele) ; NomNiveau/Couleur refletent alors le
'     modele, a titre informatif.
'   CommeModele = False (mode creation) : NomPolice/Hauteur/Largeur/Couleur/
'     NomNiveau/FondActif sont choisis par l'utilisateur dans le formulaire
'     et appliques a tous les textes crees, quelle que soit la reference.
'
' Stocke egalement la convention de formatage numerique (separateur,
' decimales) : defauts "." et 2, ajustes sur le texte source en duplication.
'==============================================================================
Option Explicit

Public CommeModele  As Boolean  ' True = memes attributs que le texte source
Public NomNiveau    As String   ' niveau du texte cree (nom ou numero)
Public Couleur      As Long     ' index couleur MicroStation 0-255
Public NomPolice    As String   ' mode creation : police ("" = police active)
Public Hauteur      As Double   ' mode creation : hauteur du texte (u.m.)
Public Largeur      As Double   ' mode creation : largeur (0 = comme hauteur)
Public FondActif    As Boolean  ' mode creation : fond/masque sous le texte

Public SepDecimal   As String   ' "." ou "," : separateur du texte cree
Public Decimales    As Integer  ' nombre de decimales du texte cree

'------------------------------------------------------------------------------
Private Sub Class_Initialize()
    InitDefauts
End Sub

'------------------------------------------------------------------------------
Sub InitDefauts()
    CommeModele = True
    NomNiveau = ""
    Couleur = 0
    NomPolice = ""
    Hauteur = 0.1
    Largeur = 0#
    FondActif = False
    SepDecimal = "."
    Decimales = 2
End Sub

'------------------------------------------------------------------------------
' Charge NomNiveau et Couleur depuis le TextElement source - uniquement en
' mode duplication, pour ne pas ecraser un choix utilisateur.
' SepDecimal et Decimales sont renseignes par CCalcul lors du parsing.
Sub ChargerDepuisElement(oText As TextElement)
    If Not CommeModele Then Exit Sub
    On Error Resume Next
    NomNiveau = oText.Level.Name
    Couleur = oText.Color
    On Error GoTo 0
End Sub

Attribute VB_Name = "RechercheAltitude"
'==============================================================================
' RechercheAltitude - Moteur de recherche des altitudes sources
'
' Detecte le texte, tag ou cellule numerique le plus proche d'un clic, dans le
' modele actif et dans les references attachees (coordonnees converties dans le
' repere du modele actif). Le resultat complet est memorise dans
' g_oSelectionCourante (voir Trans3D.bas pour les globals).
'
' Fonctions publiques :
'   TrouverAltitudeProche : point d'entree utilise par les classes de commande
'   TrouverTexteProche    : variante renvoyant le TextElement source
'==============================================================================
Option Explicit

'------------------------------------------------------------------------------
' Cherche l'altitude la plus proche (texte, cellule ou tag).
' Renvoie True si trouvee. Le resultat complet est dans g_oSelectionCourante,
' et oTextOut recoit le TextElement source (Nothing si c'est un tag).
Function TrouverAltitudeProche(oPt As Point3d, dRayon As Double, _
                                oTextOut As TextElement) As Boolean
    Set oTextOut = TrouverTexteProche(oPt, dRayon)
    TrouverAltitudeProche = g_oSelectionCourante.Trouvee
End Function

'------------------------------------------------------------------------------
' Cherche le texte numerique le plus proche du clic dans le rayon donne.
Function TrouverTexteProche(oPt As Point3d, dRayon As Double) As TextElement
    Set TrouverTexteProche = Nothing

    Dim oScan As New ElementScanCriteria
    oScan.ExcludeAllTypes
    oScan.IncludeType msdElementTypeText
    oScan.IncludeType msdElementTypeCellHeader
    oScan.IncludeType msdElementTypeTag

    Dim dMinDist As Double: dMinDist = dRayon
    Dim oBest As CAltitudeSelection
    Set oBest = New CAltitudeSelection

    ScannerAltitudeDansModele ActiveModelReference, Nothing, oScan, oPt, dMinDist, oBest

    ' Iterer par index : le For Each sur Attachments est fragile selon la
    ' version V8i, il peut echouer sans erreur visible (retour Reseaux).
    Dim oAttachments As Object
    Set oAttachments = Nothing
    On Error Resume Next
    Set oAttachments = ActiveModelReference.Attachments
    On Error GoTo 0

    Dim nCount As Long
    nCount = 0
    On Error Resume Next
    If Not oAttachments Is Nothing Then nCount = oAttachments.Count
    On Error GoTo 0

    Dim i As Long
    For i = 1 To nCount
        Dim oAtt As Object
        Set oAtt = Nothing
        On Error Resume Next
        Set oAtt = oAttachments(i)
        On Error GoTo 0
        If Not oAtt Is Nothing Then
            If AttachmentAffiche(oAtt) Then
                ScannerAltitudeDansModele oAtt, oAtt, oScan, oPt, dMinDist, oBest
            End If
        End If
    Next i

    If g_oSelectionCourante Is Nothing Then Set g_oSelectionCourante = New CAltitudeSelection
    g_oSelectionCourante.CopierDepuis oBest
    Set TrouverTexteProche = oBest.oTexte
End Function

'------------------------------------------------------------------------------
' Scanne un modele ou une reference attachee. Les points stockes dans oBest sont
' toujours exprimes dans le repere du modele actif.
Private Sub ScannerAltitudeDansModele(oModel As Object, oAttachment As Object, _
        oScan As ElementScanCriteria, oPtClic As Point3d, _
        dMinDist As Double, oBest As CAltitudeSelection)

    Dim oEnum As ElementEnumerator
    On Error Resume Next
    Set oEnum = oModel.Scan(oScan)
    If Err.Number <> 0 Or oEnum Is Nothing Then
        Err.Clear
        On Error GoTo 0
        Exit Sub
    End If
    On Error GoTo 0

    Do While oEnum.MoveNext
        Dim oElem As Element
        Set oElem = oEnum.Current

        If EstSurNiveauGele(oElem) Then GoTo SuivantElem

        If oElem.Type = msdElementTypeTag Then
            TraiterTagCandidate oElem, oAttachment, oPtClic, dMinDist, oBest

        ElseIf oElem.IsTextElement Then
            TraiterTexteCandidate oElem, oAttachment, oPtClic, dMinDist, oBest

        ElseIf oElem.Type = msdElementTypeCellHeader Then
            TraiterCelluleCandidate oElem, oAttachment, oPtClic, dMinDist, oBest
        End If
SuivantElem:
    Loop
End Sub

'------------------------------------------------------------------------------
Private Sub TraiterTagCandidate(oElem As Element, oAttachment As Object, _
        oPtClic As Point3d, dMinDist As Double, oBest As CAltitudeSelection)

    Dim oTag As TagElement
    Set oTag = oElem

    Dim sTagVal As String
    sTagVal = Trim$(CStr(oTag.Value))
    If Not g_oCalc.EstNombre(Replace(sTagVal, ",", ".")) Then Exit Sub

    Dim ptMaster As Point3d
    TransformerPointVersMaitre oAttachment, oTag.Origin, ptMaster

    Dim dD As Double
    dD = g_oCalc.Dist2D(oPtClic, ptMaster)
    If dD >= dMinDist Then Exit Sub

    dMinDist = dD
    oBest.Vider
    oBest.ValeurTexte = sTagVal
    oBest.DefinirOrigine ptMaster
    oBest.EstReference = Not (oAttachment Is Nothing)
    Set oBest.oAttachment = oAttachment

    Dim oBase As Element
    Set oBase = Nothing
    On Error Resume Next
    Set oBase = oTag.BaseElement
    On Error GoTo 0

    If Not oBase Is Nothing Then
        If oBase.Type = msdElementTypeCellHeader Then
            Set oBest.oCellule = oBase
            oBest.TagDefName = oTag.TagDefinitionName
            Exit Sub
        End If
    End If

    Set oBest.oTag = oTag
End Sub

'------------------------------------------------------------------------------
Private Sub TraiterTexteCandidate(oElem As Element, oAttachment As Object, _
        oPtClic As Point3d, dMinDist As Double, oBest As CAltitudeSelection)

    Dim oTxt As TextElement
    Set oTxt = oElem

    Dim sTxtVal As String
    sTxtVal = Trim$(oTxt.Text)
    If Not g_oCalc.EstNombre(Replace(sTxtVal, ",", ".")) Then Exit Sub

    Dim ptMaster As Point3d
    TransformerPointVersMaitre oAttachment, oTxt.Origin, ptMaster

    Dim dD As Double
    dD = g_oCalc.Dist2D(oPtClic, ptMaster)
    If dD >= dMinDist Then Exit Sub

    dMinDist = dD
    oBest.Vider
    oBest.ValeurTexte = sTxtVal
    oBest.DefinirOrigine ptMaster
    oBest.EstReference = Not (oAttachment Is Nothing)
    Set oBest.oAttachment = oAttachment
    Set oBest.oTexte = oTxt
End Sub

'------------------------------------------------------------------------------
Private Sub TraiterCelluleCandidate(oElem As Element, oAttachment As Object, _
        oPtClic As Point3d, dMinDist As Double, oBest As CAltitudeSelection)

    Dim oCell As CellElement
    Set oCell = oElem

    Dim sCellVal As String
    Dim sCellTagDef As String
    Dim oTxtCell As TextElement
    Dim ptOrigineAltitude As Point3d
    If Not ExtraireAltitudeDeCellule(oCell, sCellVal, sCellTagDef, _
                                     oTxtCell, ptOrigineAltitude) Then Exit Sub

    Dim ptMaster As Point3d
    TransformerPointVersMaitre oAttachment, ptOrigineAltitude, ptMaster

    Dim dD As Double
    dD = g_oCalc.Dist2D(oPtClic, ptMaster)
    If dD >= dMinDist Then Exit Sub

    dMinDist = dD
    oBest.Vider
    oBest.ValeurTexte = sCellVal
    oBest.TagDefName = sCellTagDef
    oBest.DefinirOrigine ptMaster
    oBest.EstReference = Not (oAttachment Is Nothing)
    Set oBest.oAttachment = oAttachment
    Set oBest.oCellule = oCell
    Set oBest.oTexte = oTxtCell
End Sub

'------------------------------------------------------------------------------
Private Function AttachmentAffiche(oAttachment As Object) As Boolean
    AttachmentAffiche = False
    On Error Resume Next
    AttachmentAffiche = CBool(oAttachment.DisplayFlag)
    If Err.Number <> 0 Then
        Err.Clear
        AttachmentAffiche = False
    End If
    On Error GoTo 0
End Function

'------------------------------------------------------------------------------
' Convertit un point issu d'une reference vers le repere du modele actif.
' Sans cette conversion, le clic est compare a des coordonnees locales de la
' reference : on detecte alors un texte numerique proche dans le mauvais repere.
' Public : utilise aussi par CGraphique pour les sommets des elements 2D.
'
' Translation reference -> master par MasterOrigin seule (KB 8.4).
' Les coordonnees scannees sont deja compatibles master : seule la
' translation d'origine est necessaire, pas de rotation ni d'echelle.
' ReferenceOrigin n'est PAS une propriete (KB 8.2) : on ne l'utilise pas.
Public Sub TransformerPointVersMaitre(oAttachment As Object, _
        oPtSource As Point3d, oPtMaster As Point3d)

    oPtMaster = oPtSource
    If oAttachment Is Nothing Then Exit Sub

    Dim ptMasterOrigin As Point3d
    ptMasterOrigin.X = 0#: ptMasterOrigin.Y = 0#: ptMasterOrigin.Z = 0#

    On Error Resume Next
    ptMasterOrigin = oAttachment.MasterOrigin
    If Err.Number <> 0 Then
        Err.Clear
        ptMasterOrigin.X = 0#: ptMasterOrigin.Y = 0#: ptMasterOrigin.Z = 0#
    End If
    On Error GoTo 0

    oPtMaster.X = ptMasterOrigin.X + oPtSource.X
    oPtMaster.Y = ptMasterOrigin.Y + oPtSource.Y
    oPtMaster.Z = ptMasterOrigin.Z + oPtSource.Z
End Sub

'------------------------------------------------------------------------------
' Teste si l'element est sur un niveau gele. Renvoie False en cas d'erreur
' (element sans niveau valide) pour ne pas bloquer le scan.
Private Function EstSurNiveauGele(oElem As Element) As Boolean
    On Error GoTo Securite
    Dim oLvl As Level
    Set oLvl = oElem.Level
    EstSurNiveauGele = Not oLvl.IsDisplayedInView(ActiveDesignFile.Views(1))
    Exit Function
Securite:
    EstSurNiveauGele = False
End Function

'------------------------------------------------------------------------------
' Parcourt les sous-elements d'une cellule et cherche une altitude numerique.
' Cherche d'abord un tag, puis un texte. Renvoie la valeur trouvee dans sVal,
' le nom de definition du tag dans sDefName (vide si c'est un texte),
' et le TextElement si c'est un texte (Nothing si c'est un tag).
Private Function ExtraireAltitudeDeCellule(oCell As CellElement, _
        sVal As String, sDefName As String, oTxtOut As TextElement, _
        ptOrigineOut As Point3d) As Boolean
    ExtraireAltitudeDeCellule = False
    sDefName = ""
    Set oTxtOut = Nothing
    ptOrigineOut = oCell.Origin

    Dim oSubEnum As ElementEnumerator
    Set oSubEnum = oCell.GetSubElements
    Do While oSubEnum.MoveNext
        If EstSurNiveauGele(oSubEnum.Current) Then GoTo SuivantSub

        ' Chercher un tag numerique
        If oSubEnum.Current.Type = msdElementTypeTag Then
            Dim oTag As TagElement
            Set oTag = oSubEnum.Current
            Dim sTV As String
            sTV = Trim$(CStr(oTag.Value))
            If g_oCalc.EstNombre(Replace(sTV, ",", ".")) Then
                sVal = sTV
                sDefName = oTag.TagDefinitionName
                ptOrigineOut = oTag.Origin
                ExtraireAltitudeDeCellule = True
                Exit Function
            End If
        End If

        ' Chercher un texte numerique
        If oSubEnum.Current.IsTextElement Then
            Dim oT As TextElement
            Set oT = oSubEnum.Current
            If g_oCalc.EstNombre(Replace(Trim$(oT.Text), ",", ".")) Then
                sVal = Trim$(oT.Text)
                Set oTxtOut = oT
                ptOrigineOut = oT.Origin
                ExtraireAltitudeDeCellule = True
                Exit Function
            End If
        End If
SuivantSub:
    Loop
End Function

Attribute VB_Name = "RechercheElement"
'==============================================================================
' RechercheElement - Recherche de l'element lineaire le plus proche d'un clic
'
' Pendant du module RechercheAltitude pour les elements convertibles :
' scanne le modele actif et, sur demande, les references attachees affichees.
' La distance clic-element est mesuree en plan sur la polyligne extraite par
' CGraphique (donc deja convertie dans le repere du modele actif).
'
' Un prefiltre sur le Range de l'element evite d'extraire la geometrie des
' elements manifestement hors du rayon de recherche (performance sur les
' gros plans).
'
' Fonction publique :
'   TrouverElementProche : renvoie l'element et son attachement (Nothing si
'                          l'element est du modele actif)
'==============================================================================
Option Explicit

'------------------------------------------------------------------------------
' Cherche l'element lineaire supporte le plus proche du clic dans le rayon
' donne. bAvecReferences : True = scanner aussi les references (Convertir),
' False = modele actif seul (Semer). Renvoie True si un element est trouve.
Public Function TrouverElementProche(oPtClic As Point3d, ByVal dRayon As Double, _
        ByVal bAvecReferences As Boolean, _
        oElemOut As Element, oAttOut As Object) As Boolean

    Set oElemOut = Nothing
    Set oAttOut = Nothing

    Dim oScan As New ElementScanCriteria
    oScan.ExcludeAllTypes
    oScan.IncludeType msdElementTypeLine
    oScan.IncludeType msdElementTypeLineString
    oScan.IncludeType msdElementTypeCurve
    oScan.IncludeType msdElementTypeArc
    oScan.IncludeType msdElementTypeEllipse
    oScan.IncludeType msdElementTypeBsplineCurve

    Dim dMinDist As Double
    dMinDist = dRayon

    ScannerElementsDansModele ActiveModelReference, Nothing, oScan, oPtClic, _
                              dRayon, dMinDist, oElemOut, oAttOut

    If bAvecReferences Then
        ' Iterer par index : le For Each sur Attachments est fragile selon la
        ' version V8i, il peut echouer sans erreur visible (retour Reseaux).
        Dim oAttachments As Object
        Set oAttachments = Nothing
        On Error Resume Next
        Set oAttachments = ActiveModelReference.Attachments
        On Error GoTo 0

        Dim nCount As Long
        nCount = 0
        On Error Resume Next
        If Not oAttachments Is Nothing Then nCount = oAttachments.Count
        On Error GoTo 0

        Dim i As Long
        For i = 1 To nCount
            Dim oAtt As Object
            Set oAtt = Nothing
            On Error Resume Next
            Set oAtt = oAttachments(i)
            On Error GoTo 0
            If Not oAtt Is Nothing Then
                If AttachmentAffiche(oAtt) Then
                    ScannerElementsDansModele oAtt, oAtt, oScan, oPtClic, _
                                              dRayon, dMinDist, oElemOut, oAttOut
                End If
            End If
        Next i
    End If

    TrouverElementProche = Not (oElemOut Is Nothing)
End Function

'------------------------------------------------------------------------------
Private Sub ScannerElementsDansModele(oModel As Object, oAttachment As Object, _
        oScan As ElementScanCriteria, oPtClic As Point3d, _
        ByVal dRayon As Double, dMinDist As Double, _
        oElemOut As Element, oAttOut As Object)

    Dim oEnum As ElementEnumerator
    On Error Resume Next
    Set oEnum = oModel.Scan(oScan)
    If Err.Number <> 0 Or oEnum Is Nothing Then
        Err.Clear
        On Error GoTo 0
        Exit Sub
    End If
    On Error GoTo 0

    Do While oEnum.MoveNext
        Dim oElem As Element
        Set oElem = oEnum.Current

        If Not HorsZone(oElem, oAttachment, oPtClic, dRayon) Then
            Dim dD As Double
            dD = DistanceElement(oElem, oAttachment, oPtClic)
            If dD >= 0# And dD < dMinDist Then
                dMinDist = dD
                Set oElemOut = oElem
                Set oAttOut = oAttachment
            End If
        End If
    Loop
End Sub

'------------------------------------------------------------------------------
' Distance en plan entre le clic et l'element (repere du modele actif).
' Renvoie -1 si la geometrie n'est pas extractible (ex. B-spline).
Private Function DistanceElement(oElem As Element, oAttachment As Object, _
                                 oPtClic As Point3d) As Double
    DistanceElement = -1#

    Dim dX() As Double, dY() As Double, dS() As Double
    If Not g_oMoteur.ExtrairePolyligne2D(oElem, oAttachment, _
            g_oSettings.dPasDiscretisation, dX, dY) Then Exit Function

    g_oCalc.AbscissesPolyligne2D dX, dY, dS

    Dim dDist As Double
    g_oCalc.AbscisseProjetee2D dX, dY, dS, oPtClic.X, oPtClic.Y, dDist
    DistanceElement = dDist
End Function

'------------------------------------------------------------------------------
' Prefiltre : True si le Range de l'element est surement hors du rayon.
' Le clic est ramene dans le repere de la reference pour la comparaison.
' En cas de doute (erreur) : False, l'element est examine.
Private Function HorsZone(oElem As Element, oAttachment As Object, _
                          oPtClic As Point3d, ByVal dRayon As Double) As Boolean
    HorsZone = False

    On Error GoTo Inconnu
    Dim oRng As Range3d
    oRng = oElem.Range

    Dim ptLocal As Point3d
    TransformerPointVersRef oAttachment, oPtClic, ptLocal

    If ptLocal.X < oRng.Low.X - dRayon Then HorsZone = True: Exit Function
    If ptLocal.X > oRng.High.X + dRayon Then HorsZone = True: Exit Function
    If ptLocal.Y < oRng.Low.Y - dRayon Then HorsZone = True: Exit Function
    If ptLocal.Y > oRng.High.Y + dRayon Then HorsZone = True: Exit Function
    Exit Function
Inconnu:
    HorsZone = False
End Function

'------------------------------------------------------------------------------
' Translation inverse master -> reference par MasterOrigin seule (KB 8.4).
Private Sub TransformerPointVersRef(oAttachment As Object, _
        oPtMaster As Point3d, oPtRef As Point3d)

    oPtRef = oPtMaster
    If oAttachment Is Nothing Then Exit Sub

    Dim ptMasterOrigin As Point3d
    ptMasterOrigin.X = 0#: ptMasterOrigin.Y = 0#: ptMasterOrigin.Z = 0#

    On Error Resume Next
    ptMasterOrigin = oAttachment.MasterOrigin
    If Err.Number <> 0 Then
        Err.Clear
        ptMasterOrigin.X = 0#: ptMasterOrigin.Y = 0#: ptMasterOrigin.Z = 0#
    End If
    On Error GoTo 0

    oPtRef.X = oPtMaster.X - ptMasterOrigin.X
    oPtRef.Y = oPtMaster.Y - ptMasterOrigin.Y
    oPtRef.Z = oPtMaster.Z - ptMasterOrigin.Z
End Sub

'------------------------------------------------------------------------------
Private Function AttachmentAffiche(oAttachment As Object) As Boolean
    AttachmentAffiche = False
    On Error Resume Next
    AttachmentAffiche = CBool(oAttachment.DisplayFlag)
    If Err.Number <> 0 Then
        Err.Clear
        AttachmentAffiche = False
    End If
    On Error GoTo 0
End Function

Attribute VB_Name = "Trans3D"
'==============================================================================
' Trans3D - Module principal - MicroStation V8i SS3 (VBA)
'
' Passage de plans 2D (en reference) vers la modelisation 3D dans le fichier
' actif. Trois commandes partagent les globals, le formulaire et les moteurs
' (cahier des charges : docs/Spec_Nouveau_Projet_VBA.md, section 1) :
'
'   Convertir : element 2D de reference -> element 3D (altitudes depart/fin
'               + intermediaires, interpolation sur abscisse curviligne)
'   Semer     : semis de points cotes le long d'un element 3D du modele actif
'               (pas fixe ou parts egales)
'   Points    : point 3D depuis une position 2D snappee + une cote du plan
'
' Regle Z commune : cercle repere au Z reel calcule, texte altitude a Z=0.00.
'
' Ce module ne contient que les globals partages, l'initialisation commune et
' les points d'entree. La recherche des cotes est dans RechercheAltitude.bas ;
' toute la logique vit dans les classes.
'
' LANCEMENT :
'   key-in : vba run [Trans3D]Convertir
'   key-in : vba run [Trans3D]Semer
'   key-in : vba run [Trans3D]Points
'==============================================================================
Option Explicit

' --- Mode de repartition du semis (CParamSemis.Mode) ---
Public Enum eModeSemis
    semisDistanceFixe = 0
    semisPartsEgales = 1
End Enum

' --- Instances partagees entre les classes de commande ---
' Chaque classe recoit ces references mais ne les cree pas.
Public g_oSettings  As CSettings         ' parametres (symbologie, semis, tolerance)
Public g_oCalc      As CCalcul           ' moteur de calcul pur
Public g_oMoteur    As CGraphique        ' moteur graphique (creation + apercus)
Public g_oSelectionCourante As CAltitudeSelection ' derniere cote trouvee (RechercheAltitude)

'==============================================================================
' Points d'entree des commandes
'==============================================================================

'------------------------------------------------------------------------------
' Convertir un element 2D de reference en element 3D
Sub Convertir()
    If Not EnvironnementPret("Trans3D - Convertir") Then Exit Sub
    InitialiserContexte
    AfficherFormulaire frmTrans3D

    CommandState.StartPrimitive New CPlacerConvertir
End Sub

'------------------------------------------------------------------------------
' Semer des points cotes le long d'un element 3D du modele actif
Sub Semer()
    If Not EnvironnementPret("Trans3D - Semer") Then Exit Sub
    InitialiserContexte
    AfficherFormulaire frmTrans3D

    CommandState.StartPrimitive New CPlacerSemis
End Sub

'------------------------------------------------------------------------------
' Creer un point 3D depuis une position 2D snappee et une cote du plan
Sub Points()
    If Not EnvironnementPret("Trans3D - Points") Then Exit Sub
    InitialiserContexte
    AfficherFormulaire frmPoints

    CommandState.StartPrimitive New CPlacerPoints
End Sub

'==============================================================================
' Initialisation commune aux trois commandes
'==============================================================================

'------------------------------------------------------------------------------
' Verifie qu'un fichier DGN est ouvert et que le modele actif est 3D.
' Trans3D travaille toujours dans un fichier 3D avec les plans 2D en reference.
Public Function EnvironnementPret(sTitre As String) As Boolean
    EnvironnementPret = False

    Dim oDgn As DesignFile
    On Error Resume Next
    Set oDgn = ActiveDesignFile
    On Error GoTo 0
    If oDgn Is Nothing Then
        MsgBox "Ouvrez d'abord un fichier DGN.", vbExclamation, sTitre
        Exit Function
    End If

    Dim bEst3D As Boolean
    bEst3D = False
    On Error Resume Next
    bEst3D = ActiveModelReference.Is3D
    On Error GoTo 0
    If Not bEst3D Then
        MsgBox "Trans3D travaille dans un modele 3D : ouvrez le fichier 3D" & _
               vbCrLf & "de travail (les plans 2D restent en reference).", _
               vbExclamation, sTitre
        Exit Function
    End If

    EnvironnementPret = True
End Function

'------------------------------------------------------------------------------
' Instanciation unique des objets partages par les classes de commande.
Public Sub InitialiserContexte()
    Set g_oSettings = New CSettings
    g_oSettings.Init

    Set g_oCalc = New CCalcul
    Set g_oMoteur = New CGraphique
    Set g_oSelectionCourante = New CAltitudeSelection

    g_oMoteur.SynchroniserRessourcesReferences
End Sub

'------------------------------------------------------------------------------
' Initialise, positionne et affiche le formulaire modeless (Tool Settings).
' oFrm en Object : pret pour frmTrans3D (etape suivante).
Public Sub AfficherFormulaire(oFrm As Object)
    oFrm.Initialiser g_oSettings
    oFrm.StartUpPosition = 0
    oFrm.Left = Application.Width * 0.6
    oFrm.Top = Application.Height * 0.05
    oFrm.Show vbModeless
End Sub

Attribute VB_Name = "frmPoints"
Attribute VB_Base = "0{2AC5559D-132D-49A0-A64C-A67B1029A8CA}{8B52DC61-7711-4960-9570-231EEAC5724C}"
Attribute VB_GlobalNameSpace = False
Attribute VB_Creatable = False
Attribute VB_PredeclaredId = True
Attribute VB_Exposed = False
Attribute VB_TemplateDerived = False
Attribute VB_Customizable = False

'==============================================================================
' frmPoints - Formulaire dedie a la commande Points (Tool Settings)
'
' Cadres :
'   Cercle repere  : creer oui/non, diametre, couleur, niveau
'   Texte altitude : creer oui/non, duplication du style de la cote source ou
'                    creation (hauteur, couleur, niveau, police, fond),
'                    decimales et separateur
'   Recherche      : tolerance de clic (u.m.)
'   Etat           : information de la commande en cours
'
' Tous les controles sont crees au runtime dans ConstruireControles
' (gardes m_bConstruit et m_bInit obligatoires, cf. spec 5.9).
' QueryClose : Cancel = 1 + Hide (jamais decharger un modeless).
'==============================================================================
Option Explicit

Private m_oSettings  As CSettings
Private m_bInit      As Boolean
Private m_bConstruit As Boolean
Private m_bAttenteZ  As Boolean

' --- Cercle repere ---
Private WithEvents chkCreerCercle As MSForms.CheckBox
Attribute chkCreerCercle.VB_VarHelpID = -1
Private WithEvents txtDiametre As MSForms.TextBox
Attribute txtDiametre.VB_VarHelpID = -1
Private WithEvents txtCouleurCercle As MSForms.TextBox
Attribute txtCouleurCercle.VB_VarHelpID = -1
Private WithEvents cmbNiveauCercle As MSForms.ComboBox
Attribute cmbNiveauCercle.VB_VarHelpID = -1
' --- Texte altitude ---
Private WithEvents chkCreerTexte As MSForms.CheckBox
Attribute chkCreerTexte.VB_VarHelpID = -1
Private WithEvents chkTexteModele As MSForms.CheckBox
Attribute chkTexteModele.VB_VarHelpID = -1
Private WithEvents txtHauteur As MSForms.TextBox
Attribute txtHauteur.VB_VarHelpID = -1
Private WithEvents txtCouleurTexte As MSForms.TextBox
Attribute txtCouleurTexte.VB_VarHelpID = -1
Private WithEvents cmbNiveauTexte As MSForms.ComboBox
Attribute cmbNiveauTexte.VB_VarHelpID = -1
Private WithEvents txtPolice As MSForms.TextBox
Attribute txtPolice.VB_VarHelpID = -1
Private WithEvents chkFond As MSForms.CheckBox
Attribute chkFond.VB_VarHelpID = -1
Private WithEvents txtDecimales As MSForms.TextBox
Attribute txtDecimales.VB_VarHelpID = -1
Private WithEvents chkVirgule As MSForms.CheckBox
Attribute chkVirgule.VB_VarHelpID = -1
' --- Recherche ---
Private WithEvents txtTolerance As MSForms.TextBox
Attribute txtTolerance.VB_VarHelpID = -1
' --- Saisie altitude ---
Private WithEvents txtSaisieZ As MSForms.TextBox
Attribute txtSaisieZ.VB_VarHelpID = -1
Private lblSaisieInfo As MSForms.Label
' --- Etat ---
Private lblEtat1     As MSForms.Label
Private lblEtat2     As MSForms.Label

'==============================================================================
' Construction des controles
'==============================================================================

Private Sub UserForm_Initialize()
    ConstruireControles
End Sub

Private Sub ConstruireControles()
    If m_bConstruit Then Exit Sub
    m_bConstruit = True

    Me.Caption = "Trans3D - Points"
    Me.Width = 212
    Me.Height = 434

    Dim dY As Double
    dY = 6

    ' --- Cadre Cercle repere --------------------------------------------------
    Dim fraCercle As MSForms.Frame
    Set fraCercle = Me.Controls.Add("Forms.Frame.1", "fraCercle")
    fraCercle.Caption = "Cercle repere (au Z reel)"
    fraCercle.Left = 6: fraCercle.Top = dY
    fraCercle.Width = 192: fraCercle.Height = 86

    Set chkCreerCercle = fraCercle.Controls.Add("Forms.CheckBox.1", "chkCreerCercle")
    chkCreerCercle.Caption = "Creer le cercle"
    chkCreerCercle.Left = 6: chkCreerCercle.Top = 10
    chkCreerCercle.Width = 180: chkCreerCercle.Height = 14

    CreerLabel fraCercle, "lblDiam", "Diametre :", 6, 28, 48
    Set txtDiametre = fraCercle.Controls.Add("Forms.TextBox.1", "txtDiametre")
    txtDiametre.Left = 56: txtDiametre.Top = 26
    txtDiametre.Width = 48: txtDiametre.Height = 16

    CreerLabel fraCercle, "lblCoulCer", "Couleur :", 6, 46, 42
    Set txtCouleurCercle = fraCercle.Controls.Add("Forms.TextBox.1", "txtCouleurCercle")
    txtCouleurCercle.Left = 56: txtCouleurCercle.Top = 44
    txtCouleurCercle.Width = 30: txtCouleurCercle.Height = 16

    CreerLabel fraCercle, "lblNivCer", "Niveau :", 6, 64, 42
    Set cmbNiveauCercle = fraCercle.Controls.Add("Forms.ComboBox.1", "cmbNiveauCercle")
    cmbNiveauCercle.Left = 56: cmbNiveauCercle.Top = 62
    cmbNiveauCercle.Width = 130: cmbNiveauCercle.Height = 16

    dY = dY + 92

    ' --- Cadre Texte altitude -------------------------------------------------
    Dim fraTexte As MSForms.Frame
    Set fraTexte = Me.Controls.Add("Forms.Frame.1", "fraTexte")
    fraTexte.Caption = "Texte altitude"
    fraTexte.Left = 6: fraTexte.Top = dY
    fraTexte.Width = 192: fraTexte.Height = 122

    Set chkCreerTexte = fraTexte.Controls.Add("Forms.CheckBox.1", "chkCreerTexte")
    chkCreerTexte.Caption = "Texte a Z=0.00 (sinon Z reel)"
    chkCreerTexte.Left = 6: chkCreerTexte.Top = 10
    chkCreerTexte.Width = 180: chkCreerTexte.Height = 14

    Set chkTexteModele = fraTexte.Controls.Add("Forms.CheckBox.1", "chkTexteModele")
    chkTexteModele.Caption = "Dupliquer le style de la cote"
    chkTexteModele.Left = 6: chkTexteModele.Top = 26
    chkTexteModele.Width = 180: chkTexteModele.Height = 14

    CreerLabel fraTexte, "lblHaut", "Hauteur :", 6, 46, 44
    Set txtHauteur = fraTexte.Controls.Add("Forms.TextBox.1", "txtHauteur")
    txtHauteur.Left = 52: txtHauteur.Top = 44
    txtHauteur.Width = 36: txtHauteur.Height = 16

    CreerLabel fraTexte, "lblCoulTxt", "Coul. :", 96, 46, 30
    Set txtCouleurTexte = fraTexte.Controls.Add("Forms.TextBox.1", "txtCouleurTexte")
    txtCouleurTexte.Left = 128: txtCouleurTexte.Top = 44
    txtCouleurTexte.Width = 28: txtCouleurTexte.Height = 16

    CreerLabel fraTexte, "lblNivTxt", "Niveau :", 6, 64, 40
    Set cmbNiveauTexte = fraTexte.Controls.Add("Forms.ComboBox.1", "cmbNiveauTexte")
    cmbNiveauTexte.Left = 52: cmbNiveauTexte.Top = 62
    cmbNiveauTexte.Width = 134: cmbNiveauTexte.Height = 16

    CreerLabel fraTexte, "lblPolice", "Police :", 6, 82, 40
    Set txtPolice = fraTexte.Controls.Add("Forms.TextBox.1", "txtPolice")
    txtPolice.Left = 52: txtPolice.Top = 80
    txtPolice.Width = 60: txtPolice.Height = 16

    Set chkFond = fraTexte.Controls.Add("Forms.CheckBox.1", "chkFond")
    chkFond.Caption = "Fond"
    chkFond.Left = 120: chkFond.Top = 81
    chkFond.Width = 60: chkFond.Height = 14

    CreerLabel fraTexte, "lblDec", "Decimales :", 6, 102, 52
    Set txtDecimales = fraTexte.Controls.Add("Forms.TextBox.1", "txtDecimales")
    txtDecimales.Left = 60: txtDecimales.Top = 100
    txtDecimales.Width = 24: txtDecimales.Height = 16

    Set chkVirgule = fraTexte.Controls.Add("Forms.CheckBox.1", "chkVirgule")
    chkVirgule.Caption = "Virgule (12,35)"
    chkVirgule.Left = 96: chkVirgule.Top = 101
    chkVirgule.Width = 90: chkVirgule.Height = 14

    dY = dY + 128

    ' --- Cadre Recherche ------------------------------------------------------
    Dim fraRech As MSForms.Frame
    Set fraRech = Me.Controls.Add("Forms.Frame.1", "fraRech")
    fraRech.Caption = "Recherche"
    fraRech.Left = 6: fraRech.Top = dY
    fraRech.Width = 192: fraRech.Height = 38

    CreerLabel fraRech, "lblTol", "Tolerance clic (u.m.) :", 6, 14, 100
    Set txtTolerance = fraRech.Controls.Add("Forms.TextBox.1", "txtTolerance")
    txtTolerance.Left = 110: txtTolerance.Top = 12
    txtTolerance.Width = 48: txtTolerance.Height = 16

    dY = dY + 44

    ' --- Cadre Saisie altitude ------------------------------------------------
    Dim fraSaisie As MSForms.Frame
    Set fraSaisie = Me.Controls.Add("Forms.Frame.1", "fraSaisie")
    fraSaisie.Caption = "Saisie altitude manuelle"
    fraSaisie.Left = 6: fraSaisie.Top = dY
    fraSaisie.Width = 192: fraSaisie.Height = 38

    CreerLabel fraSaisie, "lblZ", "Z :", 6, 14, 16
    Set txtSaisieZ = fraSaisie.Controls.Add("Forms.TextBox.1", "txtSaisieZ")
    txtSaisieZ.Left = 24: txtSaisieZ.Top = 12
    txtSaisieZ.Width = 56: txtSaisieZ.Height = 16
    txtSaisieZ.Enabled = False

    Set lblSaisieInfo = CreerLabel(fraSaisie, "lblSaisieInfo", _
        "(Enter = valider)", 86, 14, 100)

    dY = dY + 44

    ' --- Cadre Etat -----------------------------------------------------------
    Dim fraEtat As MSForms.Frame
    Set fraEtat = Me.Controls.Add("Forms.Frame.1", "fraEtat")
    fraEtat.Caption = "Etat"
    fraEtat.Left = 6: fraEtat.Top = dY
    fraEtat.Width = 192: fraEtat.Height = 54

    Set lblEtat1 = CreerLabel(fraEtat, "lblEtat1", "-", 6, 12, 180)
    Set lblEtat2 = CreerLabel(fraEtat, "lblEtat2", "-", 6, 28, 180)
End Sub

'------------------------------------------------------------------------------
Private Function CreerLabel(oParent As MSForms.Frame, sNom As String, _
                            sCaption As String, dLeft As Double, dTop As Double, _
                            dWidth As Double) As MSForms.Label
    Set CreerLabel = oParent.Controls.Add("Forms.Label.1", sNom)
    CreerLabel.Caption = sCaption
    CreerLabel.Left = dLeft: CreerLabel.Top = dTop
    CreerLabel.Width = dWidth: CreerLabel.Height = 12
End Function

'==============================================================================
' Initialisation
'==============================================================================

Sub Initialiser(oSettings As CSettings)
    ConstruireControles
    Set m_oSettings = oSettings
    m_bInit = True

    ' Cercle repere
    chkCreerCercle.Value = m_oSettings.bCreerCercle
    txtDiametre.Text = Format$(m_oSettings.oCercle.Diametre, "0.00")
    txtCouleurCercle.Text = CStr(m_oSettings.oCercle.Couleur)
    RemplirNiveaux cmbNiveauCercle

    ' Texte altitude
    chkCreerTexte.Value = m_oSettings.bTexteAZero
    chkTexteModele.Value = m_oSettings.oTexte.CommeModele
    txtHauteur.Text = Format$(m_oSettings.oTexte.Hauteur, "0.00")
    txtCouleurTexte.Text = CStr(m_oSettings.oTexte.Couleur)
    RemplirNiveaux cmbNiveauTexte
    txtPolice.Text = m_oSettings.oTexte.NomPolice
    chkFond.Value = m_oSettings.oTexte.FondActif
    txtDecimales.Text = CStr(m_oSettings.oTexte.Decimales)
    chkVirgule.Value = (m_oSettings.oTexte.SepDecimal = ",")
    ActiverChampsTexte

    ' Recherche
    txtTolerance.Text = Format$(m_oSettings.dTolTexte, "0.00")

    ReinitialiserEtat
    m_bInit = False
End Sub

'------------------------------------------------------------------------------
Private Sub RemplirNiveaux(cmb As MSForms.ComboBox)
    cmb.Clear
    cmb.AddItem ""
    On Error Resume Next
    Dim oLvl As Level
    For Each oLvl In ActiveDesignFile.Levels
        cmb.AddItem oLvl.Number & " : " & oLvl.Name
    Next
    On Error GoTo 0
    cmb.ListIndex = 0
End Sub

'------------------------------------------------------------------------------
Private Sub ActiverChampsTexte()
    Dim bLibre As Boolean
    bLibre = Not m_oSettings.oTexte.CommeModele
    txtHauteur.Enabled = bLibre
    txtCouleurTexte.Enabled = bLibre
    cmbNiveauTexte.Enabled = bLibre
    txtPolice.Enabled = bLibre
    chkFond.Enabled = bLibre
End Sub

'==============================================================================
' Mise a jour par la classe de commande
'==============================================================================

Sub AfficherElement(sTexte As String)
    If Not m_bConstruit Then Exit Sub
    lblEtat1.Caption = sTexte
End Sub

Sub AfficherZ(sTexte As String)
    If Not m_bConstruit Then Exit Sub
    lblEtat2.Caption = sTexte
End Sub

Sub ReinitialiserEtat()
    If Not m_bConstruit Then Exit Sub
    lblEtat1.Caption = "-"
    lblEtat2.Caption = "-"
End Sub

'------------------------------------------------------------------------------
' Active la saisie manuelle (appele par CPlacerPoints a l'etape 2).
Sub ActiverSaisieZ()
    If Not m_bConstruit Then Exit Sub
    m_bAttenteZ = True
    txtSaisieZ.Enabled = True
End Sub

'------------------------------------------------------------------------------
' Desactive la saisie manuelle (appele au retour etape 1).
Sub DesactiverSaisieZ()
    If Not m_bConstruit Then Exit Sub
    m_bAttenteZ = False
    txtSaisieZ.Enabled = False
    txtSaisieZ.Text = ""
End Sub

'------------------------------------------------------------------------------
' Retourne l'altitude saisie manuellement (vide = pas de saisie).
Property Get AltitudeManuelle() As String
    If Not m_bConstruit Then AltitudeManuelle = "": Exit Property
    AltitudeManuelle = Trim$(txtSaisieZ.Text)
End Property

'------------------------------------------------------------------------------
' Efface le champ apres utilisation.
Sub EffacerSaisieZ()
    If Not m_bConstruit Then Exit Sub
    txtSaisieZ.Text = ""
End Sub

Sub RafraichirTexte()
    If m_oSettings Is Nothing Then Exit Sub
    m_bInit = True
    txtCouleurTexte.Text = CStr(m_oSettings.oTexte.Couleur)
    cmbNiveauTexte.Text = m_oSettings.oTexte.NomNiveau
    txtDecimales.Text = CStr(m_oSettings.oTexte.Decimales)
    chkVirgule.Value = (m_oSettings.oTexte.SepDecimal = ",")
    m_bInit = False
End Sub

'==============================================================================
' Evenements Cercle repere
'==============================================================================

Private Sub chkCreerCercle_Change()
    If m_bInit Then Exit Sub
    If m_oSettings Is Nothing Then Exit Sub
    m_oSettings.bCreerCercle = (chkCreerCercle.Value = True)
End Sub

Private Sub txtDiametre_Change()
    If m_bInit Then Exit Sub
    If m_oSettings Is Nothing Then Exit Sub
    Dim dDiam As Double
    dDiam = Val(Replace(Trim$(txtDiametre.Text), ",", "."))
    If dDiam > 0 Then m_oSettings.oCercle.Diametre = dDiam
End Sub

Private Sub txtDiametre_KeyDown(ByVal KeyCode As MSForms.ReturnInteger, _
                                ByVal Shift As Integer)
    If KeyCode = vbKeyReturn And Not m_oSettings Is Nothing Then _
        txtDiametre.Text = Format$(m_oSettings.oCercle.Diametre, "0.00")
End Sub

Private Sub txtCouleurCercle_Change()
    If m_bInit Then Exit Sub
    If m_oSettings Is Nothing Then Exit Sub
    Dim sVal As String: sVal = Trim$(txtCouleurCercle.Text)
    If sVal = "" Then Exit Sub
    Dim nCoul As Long: nCoul = CLng(Val(sVal))
    If nCoul >= 0 And nCoul <= 255 Then m_oSettings.oCercle.Couleur = nCoul
End Sub

Private Sub cmbNiveauCercle_Change()
    If m_bInit Then Exit Sub
    If m_oSettings Is Nothing Then Exit Sub
    m_oSettings.oCercle.NomNiveau = ExtraireNiveau(cmbNiveauCercle.Text)
End Sub

'==============================================================================
' Evenements Texte altitude
'==============================================================================

Private Sub chkCreerTexte_Change()
    If m_bInit Then Exit Sub
    If m_oSettings Is Nothing Then Exit Sub
    m_oSettings.bTexteAZero = (chkCreerTexte.Value = True)
End Sub

Private Sub chkTexteModele_Change()
    If m_bInit Then Exit Sub
    If m_oSettings Is Nothing Then Exit Sub
    m_oSettings.oTexte.CommeModele = (chkTexteModele.Value = True)
    ActiverChampsTexte
    If m_oSettings.oTexte.CommeModele And m_oSettings.TextModeleDisponible Then
        m_oSettings.oTexte.ChargerDepuisElement m_oSettings.oTextModele
        RafraichirTexte
    End If
End Sub

Private Sub txtHauteur_Change()
    If m_bInit Then Exit Sub
    If m_oSettings Is Nothing Then Exit Sub
    Dim dH As Double
    dH = Val(Replace(Trim$(txtHauteur.Text), ",", "."))
    If dH > 0 Then m_oSettings.oTexte.Hauteur = dH
End Sub

Private Sub txtHauteur_KeyDown(ByVal KeyCode As MSForms.ReturnInteger, _
                               ByVal Shift As Integer)
    If KeyCode = vbKeyReturn And Not m_oSettings Is Nothing Then _
        txtHauteur.Text = Format$(m_oSettings.oTexte.Hauteur, "0.00")
End Sub

Private Sub txtCouleurTexte_Change()
    If m_bInit Then Exit Sub
    If m_oSettings Is Nothing Then Exit Sub
    Dim sVal As String: sVal = Trim$(txtCouleurTexte.Text)
    If sVal = "" Then Exit Sub
    Dim nCoul As Long: nCoul = CLng(Val(sVal))
    If nCoul >= 0 And nCoul <= 255 Then m_oSettings.oTexte.Couleur = nCoul
End Sub

Private Sub cmbNiveauTexte_Change()
    If m_bInit Then Exit Sub
    If m_oSettings Is Nothing Then Exit Sub
    m_oSettings.oTexte.NomNiveau = ExtraireNiveau(cmbNiveauTexte.Text)
End Sub

Private Sub txtPolice_Change()
    If m_bInit Then Exit Sub
    If m_oSettings Is Nothing Then Exit Sub
    m_oSettings.oTexte.NomPolice = Trim$(txtPolice.Text)
End Sub

Private Sub chkFond_Change()
    If m_bInit Then Exit Sub
    If m_oSettings Is Nothing Then Exit Sub
    m_oSettings.oTexte.FondActif = (chkFond.Value = True)
End Sub

Private Sub txtDecimales_Change()
    If m_bInit Then Exit Sub
    If m_oSettings Is Nothing Then Exit Sub
    Dim nDec As Integer
    nDec = CInt(Val(Trim$(txtDecimales.Text)))
    If nDec >= 0 And nDec <= 6 Then m_oSettings.oTexte.Decimales = nDec
End Sub

Private Sub txtDecimales_KeyDown(ByVal KeyCode As MSForms.ReturnInteger, _
                                 ByVal Shift As Integer)
    If KeyCode = vbKeyReturn And Not m_oSettings Is Nothing Then _
        txtDecimales.Text = CStr(m_oSettings.oTexte.Decimales)
End Sub

Private Sub chkVirgule_Change()
    If m_bInit Then Exit Sub
    If m_oSettings Is Nothing Then Exit Sub
    If chkVirgule.Value = True Then
        m_oSettings.oTexte.SepDecimal = ","
    Else
        m_oSettings.oTexte.SepDecimal = "."
    End If
End Sub

'==============================================================================
' Evenements Recherche
'==============================================================================

Private Sub txtTolerance_Change()
    If m_bInit Then Exit Sub
    If m_oSettings Is Nothing Then Exit Sub
    Dim dTol As Double
    dTol = Val(Replace(Trim$(txtTolerance.Text), ",", "."))
    If dTol > 0 Then m_oSettings.dTolTexte = dTol
End Sub

Private Sub txtTolerance_KeyDown(ByVal KeyCode As MSForms.ReturnInteger, _
                                 ByVal Shift As Integer)
    If KeyCode = vbKeyReturn And Not m_oSettings Is Nothing Then _
        txtTolerance.Text = Format$(m_oSettings.dTolTexte, "0.00")
End Sub

'==============================================================================
' Evenements Saisie altitude
'==============================================================================

Private Sub txtSaisieZ_KeyDown(ByVal KeyCode As MSForms.ReturnInteger, _
                               ByVal Shift As Integer)
    If KeyCode = vbKeyReturn And m_bAttenteZ Then
        If Len(Trim$(txtSaisieZ.Text)) > 0 Then
            Dim pt As Point3d
            CadInputQueue.SendDataPoint pt, 1
        End If
    End If
End Sub

'------------------------------------------------------------------------------
Private Function ExtraireNiveau(ByVal sItem As String) As String
    sItem = Trim$(sItem)
    If InStr(sItem, " : ") > 0 Then
        ExtraireNiveau = Trim$(Mid$(sItem, InStr(sItem, " : ") + 3))
    Else
        ExtraireNiveau = sItem
    End If
End Function

'==============================================================================
' Fermeture
'==============================================================================

Private Sub UserForm_QueryClose(Cancel As Integer, CloseMode As Integer)
    If CloseMode = vbFormControlMenu Then
        Cancel = 1
        Me.Hide
        CommandState.StartDefaultCommand
    End If
End Sub

Attribute VB_Name = "frmTrans3D"
Attribute VB_Base = "0{FBD108DA-4F07-4D5E-A46A-05EFAAABAD69}{289E1118-EE22-4F2C-B71D-A260D07ED045}"
Attribute VB_GlobalNameSpace = False
Attribute VB_Creatable = False
Attribute VB_PredeclaredId = True
Attribute VB_Exposed = False
Attribute VB_TemplateDerived = False
Attribute VB_Customizable = False

'==============================================================================
' frmTrans3D - Formulaire commun aux trois commandes Trans3D (Tool Settings)
'
' Cadres :
'   Texte altitude : creer oui/non, duplication du style de la cote source ou
'                    creation (hauteur, couleur, niveau, police, fond),
'                    decimales et separateur
'   Cercle repere  : creer oui/non, diametre, couleur, niveau
'   Semis          : distance fixe (pas) ou parts egales (nombre)
'   Convertir      : pas de discretisation des courbes, symbologie source
'   Recherche      : tolerance de clic (u.m.)
'   Etat           : information de la commande en cours
'
' Tous les controles sont crees au runtime dans ConstruireControles
' (gardes m_bConstruit et m_bInit obligatoires, cf. spec 5.9).
' QueryClose : Cancel = 1 + Hide (jamais decharger un modeless).
'==============================================================================
Option Explicit

Private m_oSettings  As CSettings
Private m_bInit      As Boolean
Private m_bConstruit As Boolean

' --- Texte altitude ---
Private WithEvents chkCreerTexte As MSForms.CheckBox
Attribute chkCreerTexte.VB_VarHelpID = -1
Private WithEvents chkTexteModele As MSForms.CheckBox
Attribute chkTexteModele.VB_VarHelpID = -1
Private WithEvents txtHauteur As MSForms.TextBox
Attribute txtHauteur.VB_VarHelpID = -1
Private WithEvents txtCouleurTexte As MSForms.TextBox
Attribute txtCouleurTexte.VB_VarHelpID = -1
Private WithEvents cmbNiveauTexte As MSForms.ComboBox
Attribute cmbNiveauTexte.VB_VarHelpID = -1
Private WithEvents txtPolice As MSForms.TextBox
Attribute txtPolice.VB_VarHelpID = -1
Private WithEvents chkFond As MSForms.CheckBox
Attribute chkFond.VB_VarHelpID = -1
Private WithEvents txtDecimales As MSForms.TextBox
Attribute txtDecimales.VB_VarHelpID = -1
Private WithEvents chkVirgule As MSForms.CheckBox
Attribute chkVirgule.VB_VarHelpID = -1
' --- Cercle repere ---
Private WithEvents chkCreerCercle As MSForms.CheckBox
Attribute chkCreerCercle.VB_VarHelpID = -1
Private WithEvents txtDiametre As MSForms.TextBox
Attribute txtDiametre.VB_VarHelpID = -1
Private WithEvents txtCouleurCercle As MSForms.TextBox
Attribute txtCouleurCercle.VB_VarHelpID = -1
Private WithEvents cmbNiveauCercle As MSForms.ComboBox
Attribute cmbNiveauCercle.VB_VarHelpID = -1
' --- Decoupage ---
Private WithEvents chkDecoupage As MSForms.CheckBox
Attribute chkDecoupage.VB_VarHelpID = -1
Private WithEvents optPasFixe As MSForms.OptionButton
Attribute optPasFixe.VB_VarHelpID = -1
Private WithEvents optPartsEgales As MSForms.OptionButton
Attribute optPartsEgales.VB_VarHelpID = -1
Private WithEvents txtPas As MSForms.TextBox
Attribute txtPas.VB_VarHelpID = -1
Private WithEvents txtNombre As MSForms.TextBox
Attribute txtNombre.VB_VarHelpID = -1
' --- Convertir ---
Private WithEvents txtDiscret As MSForms.TextBox
Attribute txtDiscret.VB_VarHelpID = -1
Private WithEvents chkSymboSource As MSForms.CheckBox
Attribute chkSymboSource.VB_VarHelpID = -1
' --- Recherche ---
Private WithEvents txtTolerance As MSForms.TextBox
Attribute txtTolerance.VB_VarHelpID = -1
' --- Etat ---
Private lblEtat1     As MSForms.Label   ' element selectionne (type, longueur)
Private lblEtat2     As MSForms.Label   ' altitudes depart / arrivee

'==============================================================================
' Construction des controles
'==============================================================================

Private Sub UserForm_Initialize()
    ConstruireControles
End Sub

Private Sub ConstruireControles()
    If m_bConstruit Then Exit Sub
    m_bConstruit = True

    Me.Caption = "Trans3D"
    Me.Width = 212
    Me.Height = 514

    Dim dY As Double
    dY = 6

    ' --- Cadre Texte altitude -------------------------------------------------
    Dim fraTexte As MSForms.Frame
    Set fraTexte = Me.Controls.Add("Forms.Frame.1", "fraTexte")
    fraTexte.Caption = "Texte altitude"
    fraTexte.Left = 6: fraTexte.Top = dY
    fraTexte.Width = 192: fraTexte.Height = 122

    Set chkCreerTexte = fraTexte.Controls.Add("Forms.CheckBox.1", "chkCreerTexte")
    chkCreerTexte.Caption = "Texte a Z=0.00 (sinon Z reel)"
    chkCreerTexte.Left = 6: chkCreerTexte.Top = 10
    chkCreerTexte.Width = 180: chkCreerTexte.Height = 14

    Set chkTexteModele = fraTexte.Controls.Add("Forms.CheckBox.1", "chkTexteModele")
    chkTexteModele.Caption = "Dupliquer le style de la cote"
    chkTexteModele.Left = 6: chkTexteModele.Top = 26
    chkTexteModele.Width = 180: chkTexteModele.Height = 14

    CreerLabel fraTexte, "lblHaut", "Hauteur :", 6, 46, 44
    Set txtHauteur = fraTexte.Controls.Add("Forms.TextBox.1", "txtHauteur")
    txtHauteur.Left = 52: txtHauteur.Top = 44
    txtHauteur.Width = 36: txtHauteur.Height = 16

    CreerLabel fraTexte, "lblCoulTxt", "Coul. :", 96, 46, 30
    Set txtCouleurTexte = fraTexte.Controls.Add("Forms.TextBox.1", "txtCouleurTexte")
    txtCouleurTexte.Left = 128: txtCouleurTexte.Top = 44
    txtCouleurTexte.Width = 28: txtCouleurTexte.Height = 16

    CreerLabel fraTexte, "lblNivTxt", "Niveau :", 6, 64, 40
    Set cmbNiveauTexte = fraTexte.Controls.Add("Forms.ComboBox.1", "cmbNiveauTexte")
    cmbNiveauTexte.Left = 52: cmbNiveauTexte.Top = 62
    cmbNiveauTexte.Width = 134: cmbNiveauTexte.Height = 16

    CreerLabel fraTexte, "lblPolice", "Police :", 6, 82, 40
    Set txtPolice = fraTexte.Controls.Add("Forms.TextBox.1", "txtPolice")
    txtPolice.Left = 52: txtPolice.Top = 80
    txtPolice.Width = 60: txtPolice.Height = 16

    Set chkFond = fraTexte.Controls.Add("Forms.CheckBox.1", "chkFond")
    chkFond.Caption = "Fond"
    chkFond.Left = 120: chkFond.Top = 81
    chkFond.Width = 60: chkFond.Height = 14

    CreerLabel fraTexte, "lblDec", "Decimales :", 6, 102, 52
    Set txtDecimales = fraTexte.Controls.Add("Forms.TextBox.1", "txtDecimales")
    txtDecimales.Left = 60: txtDecimales.Top = 100
    txtDecimales.Width = 24: txtDecimales.Height = 16

    Set chkVirgule = fraTexte.Controls.Add("Forms.CheckBox.1", "chkVirgule")
    chkVirgule.Caption = "Virgule (12,35)"
    chkVirgule.Left = 96: chkVirgule.Top = 101
    chkVirgule.Width = 90: chkVirgule.Height = 14

    dY = dY + 128

    ' --- Cadre Cercle repere --------------------------------------------------
    Dim fraCercle As MSForms.Frame
    Set fraCercle = Me.Controls.Add("Forms.Frame.1", "fraCercle")
    fraCercle.Caption = "Cercle repere (au Z reel)"
    fraCercle.Left = 6: fraCercle.Top = dY
    fraCercle.Width = 192: fraCercle.Height = 86

    Set chkCreerCercle = fraCercle.Controls.Add("Forms.CheckBox.1", "chkCreerCercle")
    chkCreerCercle.Caption = "Creer le cercle"
    chkCreerCercle.Left = 6: chkCreerCercle.Top = 10
    chkCreerCercle.Width = 180: chkCreerCercle.Height = 14

    CreerLabel fraCercle, "lblDiam", "Diametre :", 6, 28, 48
    Set txtDiametre = fraCercle.Controls.Add("Forms.TextBox.1", "txtDiametre")
    txtDiametre.Left = 56: txtDiametre.Top = 26
    txtDiametre.Width = 48: txtDiametre.Height = 16

    CreerLabel fraCercle, "lblCoulCer", "Couleur :", 6, 46, 42
    Set txtCouleurCercle = fraCercle.Controls.Add("Forms.TextBox.1", "txtCouleurCercle")
    txtCouleurCercle.Left = 56: txtCouleurCercle.Top = 44
    txtCouleurCercle.Width = 30: txtCouleurCercle.Height = 16

    CreerLabel fraCercle, "lblNivCer", "Niveau :", 6, 64, 42
    Set cmbNiveauCercle = fraCercle.Controls.Add("Forms.ComboBox.1", "cmbNiveauCercle")
    cmbNiveauCercle.Left = 56: cmbNiveauCercle.Top = 62
    cmbNiveauCercle.Width = 130: cmbNiveauCercle.Height = 16

    dY = dY + 92

    ' --- Cadre Decoupage ------------------------------------------------------
    Dim fraDecoupage As MSForms.Frame
    Set fraDecoupage = Me.Controls.Add("Forms.Frame.1", "fraDecoupage")
    fraDecoupage.Caption = "Decoupage"
    fraDecoupage.Left = 6: fraDecoupage.Top = dY
    fraDecoupage.Width = 192: fraDecoupage.Height = 74

    Set chkDecoupage = fraDecoupage.Controls.Add("Forms.CheckBox.1", "chkDecoupage")
    chkDecoupage.Caption = "Creer des points intermediaires"
    chkDecoupage.Left = 6: chkDecoupage.Top = 10
    chkDecoupage.Width = 180: chkDecoupage.Height = 14

    Set optPasFixe = fraDecoupage.Controls.Add("Forms.OptionButton.1", "optPasFixe")
    optPasFixe.Caption = "Distance fixe (m)"
    optPasFixe.Left = 6: optPasFixe.Top = 28
    optPasFixe.Width = 110: optPasFixe.Height = 14

    Set txtPas = fraDecoupage.Controls.Add("Forms.TextBox.1", "txtPas")
    txtPas.Left = 130: txtPas.Top = 27
    txtPas.Width = 48: txtPas.Height = 16

    Set optPartsEgales = fraDecoupage.Controls.Add("Forms.OptionButton.1", "optPartsEgales")
    optPartsEgales.Caption = "Nombre de points"
    optPartsEgales.Left = 6: optPartsEgales.Top = 48
    optPartsEgales.Width = 110: optPartsEgales.Height = 14

    Set txtNombre = fraDecoupage.Controls.Add("Forms.TextBox.1", "txtNombre")
    txtNombre.Left = 130: txtNombre.Top = 47
    txtNombre.Width = 48: txtNombre.Height = 16

    dY = dY + 80

    ' --- Cadre Convertir ------------------------------------------------------
    Dim fraConv As MSForms.Frame
    Set fraConv = Me.Controls.Add("Forms.Frame.1", "fraConv")
    fraConv.Caption = "Convertir"
    fraConv.Left = 6: fraConv.Top = dY
    fraConv.Width = 192: fraConv.Height = 56

    CreerLabel fraConv, "lblDiscret", "Pas discretisation :", 6, 12, 88
    Set txtDiscret = fraConv.Controls.Add("Forms.TextBox.1", "txtDiscret")
    txtDiscret.Left = 98: txtDiscret.Top = 10
    txtDiscret.Width = 48: txtDiscret.Height = 16

    Set chkSymboSource = fraConv.Controls.Add("Forms.CheckBox.1", "chkSymboSource")
    chkSymboSource.Caption = "Symbologie de l'element source"
    chkSymboSource.Left = 6: chkSymboSource.Top = 32
    chkSymboSource.Width = 180: chkSymboSource.Height = 14

    dY = dY + 62

    ' --- Cadre Recherche ------------------------------------------------------
    Dim fraRech As MSForms.Frame
    Set fraRech = Me.Controls.Add("Forms.Frame.1", "fraRech")
    fraRech.Caption = "Recherche"
    fraRech.Left = 6: fraRech.Top = dY
    fraRech.Width = 192: fraRech.Height = 38

    CreerLabel fraRech, "lblTol", "Tolerance clic (u.m.) :", 6, 14, 100
    Set txtTolerance = fraRech.Controls.Add("Forms.TextBox.1", "txtTolerance")
    txtTolerance.Left = 110: txtTolerance.Top = 12
    txtTolerance.Width = 48: txtTolerance.Height = 16

    dY = dY + 44

    ' --- Cadre Etat -----------------------------------------------------------
    Dim fraEtat As MSForms.Frame
    Set fraEtat = Me.Controls.Add("Forms.Frame.1", "fraEtat")
    fraEtat.Caption = "Etat"
    fraEtat.Left = 6: fraEtat.Top = dY
    fraEtat.Width = 192: fraEtat.Height = 54

    Set lblEtat1 = CreerLabel(fraEtat, "lblEtat1", "-", 6, 12, 180)
    Set lblEtat2 = CreerLabel(fraEtat, "lblEtat2", "-", 6, 28, 180)
End Sub

'------------------------------------------------------------------------------
Private Function CreerLabel(oParent As MSForms.Frame, sNom As String, _
                            sCaption As String, dLeft As Double, dTop As Double, _
                            dWidth As Double) As MSForms.Label
    Set CreerLabel = oParent.Controls.Add("Forms.Label.1", sNom)
    CreerLabel.Caption = sCaption
    CreerLabel.Left = dLeft: CreerLabel.Top = dTop
    CreerLabel.Width = dWidth: CreerLabel.Height = 12
End Function

'==============================================================================
' Initialisation
'==============================================================================

Sub Initialiser(oSettings As CSettings)
    ConstruireControles
    Set m_oSettings = oSettings
    m_bInit = True

    ' Texte altitude
    chkCreerTexte.Value = m_oSettings.bTexteAZero
    chkTexteModele.Value = m_oSettings.oTexte.CommeModele
    txtHauteur.Text = Format$(m_oSettings.oTexte.Hauteur, "0.00")
    txtCouleurTexte.Text = CStr(m_oSettings.oTexte.Couleur)
    RemplirNiveaux cmbNiveauTexte
    txtPolice.Text = m_oSettings.oTexte.NomPolice
    chkFond.Value = m_oSettings.oTexte.FondActif
    txtDecimales.Text = CStr(m_oSettings.oTexte.Decimales)
    chkVirgule.Value = (m_oSettings.oTexte.SepDecimal = ",")
    ActiverChampsTexte

    ' Cercle repere
    chkCreerCercle.Value = m_oSettings.bCreerCercle
    txtDiametre.Text = Format$(m_oSettings.oCercle.Diametre, "0.00")
    txtCouleurCercle.Text = CStr(m_oSettings.oCercle.Couleur)
    RemplirNiveaux cmbNiveauCercle

    ' Decoupage
    chkDecoupage.Value = m_oSettings.bDecoupage
    optPasFixe.Value = (m_oSettings.oSemis.Mode = semisDistanceFixe)
    optPartsEgales.Value = (m_oSettings.oSemis.Mode = semisPartsEgales)
    txtPas.Text = Format$(m_oSettings.oSemis.Pas, "0.00")
    txtNombre.Text = CStr(m_oSettings.oSemis.Nombre)
    ActiverChampsDecoupage

    ' Convertir
    txtDiscret.Text = Format$(m_oSettings.dPasDiscretisation, "0.00")
    chkSymboSource.Value = m_oSettings.bSymboSource

    ' Recherche
    txtTolerance.Text = Format$(m_oSettings.dTolTexte, "0.00")

    ReinitialiserEtat
    m_bInit = False
End Sub

'------------------------------------------------------------------------------
Private Sub RemplirNiveaux(cmb As MSForms.ComboBox)
    cmb.Clear
    cmb.AddItem ""
    On Error Resume Next
    Dim oLvl As Level
    For Each oLvl In ActiveDesignFile.Levels
        cmb.AddItem oLvl.Number & " : " & oLvl.Name
    Next
    On Error GoTo 0
    cmb.ListIndex = 0
End Sub

'------------------------------------------------------------------------------
' Les champs de style ne sont saisissables qu'en mode creation.
Private Sub ActiverChampsTexte()
    Dim bLibre As Boolean
    bLibre = Not m_oSettings.oTexte.CommeModele
    txtHauteur.Enabled = bLibre
    txtCouleurTexte.Enabled = bLibre
    cmbNiveauTexte.Enabled = bLibre
    txtPolice.Enabled = bLibre
    chkFond.Enabled = bLibre
End Sub

'------------------------------------------------------------------------------
Private Sub ActiverChampsDecoupage()
    Dim bActif As Boolean
    bActif = m_oSettings.bDecoupage
    optPasFixe.Enabled = bActif
    optPartsEgales.Enabled = bActif
    txtPas.Enabled = bActif And (m_oSettings.oSemis.Mode = semisDistanceFixe)
    txtNombre.Enabled = bActif And (m_oSettings.oSemis.Mode = semisPartsEgales)
End Sub

'==============================================================================
' Mise a jour par les classes de commande
'==============================================================================

'------------------------------------------------------------------------------
' Ligne 1 du cadre Etat : element selectionne (type, longueur).
Sub AfficherElement(sTexte As String)
    If Not m_bConstruit Then Exit Sub
    lblEtat1.Caption = sTexte
End Sub

'------------------------------------------------------------------------------
' Ligne 2 du cadre Etat : altitudes depart / arrivee, pente.
Sub AfficherZ(sTexte As String)
    If Not m_bConstruit Then Exit Sub
    lblEtat2.Caption = sTexte
End Sub

'------------------------------------------------------------------------------
' Appele par les classes de commande au Reset (spec 5.9).
Sub ReinitialiserEtat()
    If Not m_bConstruit Then Exit Sub
    lblEtat1.Caption = "-"
    lblEtat2.Caption = "-"
End Sub

'------------------------------------------------------------------------------
' Recale les champs texte apres lecture d'une cote source (mode duplication).
Sub RafraichirTexte()
    If m_oSettings Is Nothing Then Exit Sub
    m_bInit = True
    txtCouleurTexte.Text = CStr(m_oSettings.oTexte.Couleur)
    cmbNiveauTexte.Text = m_oSettings.oTexte.NomNiveau
    txtDecimales.Text = CStr(m_oSettings.oTexte.Decimales)
    chkVirgule.Value = (m_oSettings.oTexte.SepDecimal = ",")
    m_bInit = False
End Sub

'==============================================================================
' Evenements Texte altitude
'==============================================================================

Private Sub chkCreerTexte_Change()
    If m_bInit Then Exit Sub
    If m_oSettings Is Nothing Then Exit Sub
    m_oSettings.bTexteAZero = (chkCreerTexte.Value = True)
End Sub

Private Sub chkTexteModele_Change()
    If m_bInit Then Exit Sub
    If m_oSettings Is Nothing Then Exit Sub
    m_oSettings.oTexte.CommeModele = (chkTexteModele.Value = True)
    ActiverChampsTexte
    If m_oSettings.oTexte.CommeModele And m_oSettings.TextModeleDisponible Then
        m_oSettings.oTexte.ChargerDepuisElement m_oSettings.oTextModele
        RafraichirTexte
    End If
End Sub

Private Sub txtHauteur_Change()
    If m_bInit Then Exit Sub
    If m_oSettings Is Nothing Then Exit Sub
    Dim dH As Double
    dH = Val(Replace(Trim$(txtHauteur.Text), ",", "."))
    If dH > 0 Then m_oSettings.oTexte.Hauteur = dH
End Sub

Private Sub txtHauteur_KeyDown(ByVal KeyCode As MSForms.ReturnInteger, _
                               ByVal Shift As Integer)
    If KeyCode = vbKeyReturn And Not m_oSettings Is Nothing Then _
        txtHauteur.Text = Format$(m_oSettings.oTexte.Hauteur, "0.00")
End Sub

Private Sub txtCouleurTexte_Change()
    If m_bInit Then Exit Sub
    If m_oSettings Is Nothing Then Exit Sub
    Dim sVal As String: sVal = Trim$(txtCouleurTexte.Text)
    If sVal = "" Then Exit Sub
    Dim nCoul As Long: nCoul = CLng(Val(sVal))
    If nCoul >= 0 And nCoul <= 255 Then m_oSettings.oTexte.Couleur = nCoul
End Sub

Private Sub cmbNiveauTexte_Change()
    If m_bInit Then Exit Sub
    If m_oSettings Is Nothing Then Exit Sub
    m_oSettings.oTexte.NomNiveau = ExtraireNiveau(cmbNiveauTexte.Text)
End Sub

Private Sub txtPolice_Change()
    If m_bInit Then Exit Sub
    If m_oSettings Is Nothing Then Exit Sub
    m_oSettings.oTexte.NomPolice = Trim$(txtPolice.Text)
End Sub

Private Sub chkFond_Change()
    If m_bInit Then Exit Sub
    If m_oSettings Is Nothing Then Exit Sub
    m_oSettings.oTexte.FondActif = (chkFond.Value = True)
End Sub

Private Sub txtDecimales_Change()
    If m_bInit Then Exit Sub
    If m_oSettings Is Nothing Then Exit Sub
    Dim nDec As Integer
    nDec = CInt(Val(Trim$(txtDecimales.Text)))
    If nDec >= 0 And nDec <= 6 Then m_oSettings.oTexte.Decimales = nDec
End Sub

Private Sub txtDecimales_KeyDown(ByVal KeyCode As MSForms.ReturnInteger, _
                                 ByVal Shift As Integer)
    If KeyCode = vbKeyReturn And Not m_oSettings Is Nothing Then _
        txtDecimales.Text = CStr(m_oSettings.oTexte.Decimales)
End Sub

Private Sub chkVirgule_Change()
    If m_bInit Then Exit Sub
    If m_oSettings Is Nothing Then Exit Sub
    If chkVirgule.Value = True Then
        m_oSettings.oTexte.SepDecimal = ","
    Else
        m_oSettings.oTexte.SepDecimal = "."
    End If
End Sub

'==============================================================================
' Evenements Cercle repere
'==============================================================================

Private Sub chkCreerCercle_Change()
    If m_bInit Then Exit Sub
    If m_oSettings Is Nothing Then Exit Sub
    m_oSettings.bCreerCercle = (chkCreerCercle.Value = True)
End Sub

Private Sub txtDiametre_Change()
    If m_bInit Then Exit Sub
    If m_oSettings Is Nothing Then Exit Sub
    Dim dDiam As Double
    dDiam = Val(Replace(Trim$(txtDiametre.Text), ",", "."))
    If dDiam > 0 Then m_oSettings.oCercle.Diametre = dDiam
End Sub

Private Sub txtDiametre_KeyDown(ByVal KeyCode As MSForms.ReturnInteger, _
                                ByVal Shift As Integer)
    If KeyCode = vbKeyReturn And Not m_oSettings Is Nothing Then _
        txtDiametre.Text = Format$(m_oSettings.oCercle.Diametre, "0.00")
End Sub

Private Sub txtCouleurCercle_Change()
    If m_bInit Then Exit Sub
    If m_oSettings Is Nothing Then Exit Sub
    Dim sVal As String: sVal = Trim$(txtCouleurCercle.Text)
    If sVal = "" Then Exit Sub
    Dim nCoul As Long: nCoul = CLng(Val(sVal))
    If nCoul >= 0 And nCoul <= 255 Then m_oSettings.oCercle.Couleur = nCoul
End Sub

Private Sub cmbNiveauCercle_Change()
    If m_bInit Then Exit Sub
    If m_oSettings Is Nothing Then Exit Sub
    m_oSettings.oCercle.NomNiveau = ExtraireNiveau(cmbNiveauCercle.Text)
End Sub

'==============================================================================
' Evenements Decoupage
'==============================================================================

Private Sub chkDecoupage_Change()
    If m_bInit Then Exit Sub
    If m_oSettings Is Nothing Then Exit Sub
    m_oSettings.bDecoupage = (chkDecoupage.Value = True)
    ActiverChampsDecoupage
End Sub

Private Sub optPasFixe_Change()
    If m_bInit Then Exit Sub
    If m_oSettings Is Nothing Then Exit Sub
    If optPasFixe.Value = True Then m_oSettings.oSemis.Mode = semisDistanceFixe
    ActiverChampsDecoupage
End Sub

Private Sub optPartsEgales_Change()
    If m_bInit Then Exit Sub
    If m_oSettings Is Nothing Then Exit Sub
    If optPartsEgales.Value = True Then m_oSettings.oSemis.Mode = semisPartsEgales
    ActiverChampsDecoupage
End Sub

Private Sub txtPas_Change()
    If m_bInit Then Exit Sub
    If m_oSettings Is Nothing Then Exit Sub
    Dim dPas As Double
    dPas = Val(Replace(Trim$(txtPas.Text), ",", "."))
    If dPas > 0 Then m_oSettings.oSemis.Pas = dPas
End Sub

Private Sub txtPas_KeyDown(ByVal KeyCode As MSForms.ReturnInteger, _
                           ByVal Shift As Integer)
    If KeyCode = vbKeyReturn And Not m_oSettings Is Nothing Then _
        txtPas.Text = Format$(m_oSettings.oSemis.Pas, "0.00")
End Sub

Private Sub txtNombre_Change()
    If m_bInit Then Exit Sub
    If m_oSettings Is Nothing Then Exit Sub
    Dim nNb As Long
    nNb = CLng(Val(Trim$(txtNombre.Text)))
    If nNb >= 1 Then m_oSettings.oSemis.Nombre = nNb
End Sub

Private Sub txtNombre_KeyDown(ByVal KeyCode As MSForms.ReturnInteger, _
                              ByVal Shift As Integer)
    If KeyCode = vbKeyReturn And Not m_oSettings Is Nothing Then _
        txtNombre.Text = CStr(m_oSettings.oSemis.Nombre)
End Sub

'==============================================================================
' Evenements Convertir
'==============================================================================

Private Sub txtDiscret_Change()
    If m_bInit Then Exit Sub
    If m_oSettings Is Nothing Then Exit Sub
    Dim dPas As Double
    dPas = Val(Replace(Trim$(txtDiscret.Text), ",", "."))
    If dPas > 0 Then m_oSettings.dPasDiscretisation = dPas
End Sub

Private Sub txtDiscret_KeyDown(ByVal KeyCode As MSForms.ReturnInteger, _
                               ByVal Shift As Integer)
    If KeyCode = vbKeyReturn And Not m_oSettings Is Nothing Then _
        txtDiscret.Text = Format$(m_oSettings.dPasDiscretisation, "0.00")
End Sub

Private Sub chkSymboSource_Change()
    If m_bInit Then Exit Sub
    If m_oSettings Is Nothing Then Exit Sub
    m_oSettings.bSymboSource = (chkSymboSource.Value = True)
End Sub

'==============================================================================
' Evenements Recherche
'==============================================================================

Private Sub txtTolerance_Change()
    If m_bInit Then Exit Sub
    If m_oSettings Is Nothing Then Exit Sub
    Dim dTol As Double
    dTol = Val(Replace(Trim$(txtTolerance.Text), ",", "."))
    If dTol > 0 Then m_oSettings.dTolTexte = dTol
End Sub

Private Sub txtTolerance_KeyDown(ByVal KeyCode As MSForms.ReturnInteger, _
                                 ByVal Shift As Integer)
    If KeyCode = vbKeyReturn And Not m_oSettings Is Nothing Then _
        txtTolerance.Text = Format$(m_oSettings.dTolTexte, "0.00")
End Sub

'------------------------------------------------------------------------------
' Extrait le nom du niveau d'un item "numero : nom" de combo.
Private Function ExtraireNiveau(ByVal sItem As String) As String
    sItem = Trim$(sItem)
    If InStr(sItem, " : ") > 0 Then
        ExtraireNiveau = Trim$(Mid$(sItem, InStr(sItem, " : ") + 3))
    Else
        ExtraireNiveau = sItem
    End If
End Function

'==============================================================================
' Fermeture
'==============================================================================

Private Sub UserForm_QueryClose(Cancel As Integer, CloseMode As Integer)
    If CloseMode = vbFormControlMenu Then
        Cancel = 1
        Me.Hide
        CommandState.StartDefaultCommand
    End If
End Sub
